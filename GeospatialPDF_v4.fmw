FME workspace GeospatialPDF_v4.fmw
Title: Geospatial PDF - Cartographic Output

Parameters:
- SourceDataset_JPEG2000 = $(FME_MF_DIR)output_ID_nt\04_Basemap\subtiles\subbasemap_ID_nt_2.jp2   # Source JPEG 2000 File(s)
- Zoom = 11   # Zoom of the basemap
- FILE_name = BoundingBox   # Choose filename
- DestDataset_PDF2D = $(FME_MF_DIR)output_DK\05_EXPORT_PDF\$(FILE_name)_PDF.pdf   # Destination Adobe Geospatial PDF File
- Tile_num = 4   # Part of the boundingbox
- SQUARE_SIZE_KM = 15   # Square size [km]
- Features_to_print = power waterway boundary building emergency highway public_transport railway   # Features to put on PDF
- Number_of_features = 26   # Number of features
- Layer_feature = $(FME_MF_DIR)output   # Source of the layer to map
- DATE = 20220622   # Date 
- ISO = ID_nt   # ISO code
- SourceDataset_PDF2D = $(FME_MF_DIR)PDF_legend.pdf   # Source Adobe Geospatial PDF File
- ISO3 = CHE_FRA   # Countries
- GEOM = 20.61289497793364 41.89173351572744 20.69 41.93173351572744   # BoundingBox

Readers:
- JPEG2000_1: JPEG2000 from $(SourceDataset_JPEG2000) in LL-WGS84
- PDF2D_1: PDF2D from $(FME_MF_DIR)PDF_legend.pdf
- ARCGIS_LAYER_1: ARCGIS_LAYER from C:\Users\alexandre\Downloads\World_Continents.lpk
- PDF2D_2: PDF2D from $(SourceDataset_PDF2D)

Writers:
- PDF2D_3: PDF2D to $(DestDataset_PDF2D)

JPEG2000 (reader JPEG2000_1)
    -> BoundingBoxAccumulator
    -> AttributeCreator
BoundingBoxAccumulator
    ACCUM_ATTRS_NAME = Use Attributes From One Feature
    BOUNDING_BOX -> Sorter
    BOUNDING_BOX -> AttributeCreator_2
    BOUNDING_BOX -> Clipper_4 [CLIPPER]
Note: Sort drawing order with _order
Sorter
    SORT_PARM = _order NUMERIC ASCENDING
    SORTED -> PDFPageFormatter [Main]
Creator_9
    COORDS = $(GEOM)
    COORDSYS = LL-WGS84
    GEOMTYPE = 2D Min/Max Box
    NUM = 1
    CREATED -> FeatureReader [INITIATOR]
    CREATED -> Cloner_8
FeatureReader
    ATTRIBUTES = TOPO-OSM-WMS,"wms_service_name,wms_service_title,wms_service_abstract,wms_layer_name,wms_layer_title,wms_layer_abstract,wms_selected_layers,fme_geometry{0}"
    ATTR_ACCUM_MODE = Only Use Result
    COMBINE_GEOM = Use Result
    DATASET = http://ows.mundialis.de/services/service?
    FEATURETYPES = TOPO-OSM-WMS
    FORMAT = WMS
    INTERACT = Bounding Boxes Intersect
    OUTPUT_FEATURES_DISPLAY = Schema and Data Features
    WMS_MAP_FORMAT = image/png
    WMS_PIPE_DELIM = yes
    WMS_READER_META_ATTRIBUTES = fme_dataset fme_basename
    WMS_SPLIT_REQUEST = no
    WMS_SRS = EPSG:4326
    WMS_TRANSPARENT = no
    WMS_USE_SEARCH_ENVELOPE = NO
    WMS_WMS_LAYER_LIST = "{OpenStreetMap WMS}|{TOPO-OSM-WMS}"
    TOPO-OSM-WMS -> AttributeManager_10
AttributeManager_10
    ATTR_TABLE = SET_TO _order = 1
    -> Sorter_4
Cloner_8
    COPIES = 3
    COPYATT = _copynum
    COPY -> TestFilter_6
TestFilter_6
    DEFAULT_VALUE = <UNFILTERED>
    TEST_LIST = "BOOL_OP,OR,COMPOSITE_TEST,""""""1"""""",TEST_CLAUSE,TEST @Value(_copynum) = 0",@Value(_copynum) = 0,"BOOL_OP,OR,COMPOSITE_TEST,""""""1"""""",TEST_CLAUSE,TEST @Value(_copynum) = 1",@Value(_copynum) = 1
    @Value(_copynum) = 1 -> BoundsExtractor
    <UNFILTERED> -> BoundsExtractor_2
BoundsExtractor
    XMAX = _xmax
    XMIN = _xmin
    YMAX = _ymax
    YMIN = _ymin
    ZMAX = _zmax
    ZMIN = _zmin
    -> Cloner_9
Cloner_9
    COPIES = 5
    COPYATT = _copynum2
    COPY -> AttributeManager_6
AttributeManager_6
    ATTR_TABLE:
      SET_TO x = FME_CONDITIONAL:DEFAULT_VALUE'@sub(@Value(_xmin),1.2*@sub(@Value(_xmax),@Value(_xmin)))'BOOL_OP;OR;COMPOSITE_TEST;1 OR 2;TEST @Value(_copynum2) = 0;TEST @Value(_copynum2) = 4'@sub(@Value(_xmin),1.2*@sub(@Value(_xmax),@Value(_xmin)))'BOOL_OP;OR;COMPOSITE_TEST;1;TEST @Value(_copynum2) = 1'@sum(@Value(_xmax),1.2*@sub(@Value(_xmax),@Value(_xmin)))'BOOL_OP;OR;COMPOSITE_TEST;1;TEST @Value(_copynum2) = 2'@sum(@Value(_xmax),1.2*@sub(@Value(_xmax),@Value(_xmin)))'FME_NUM_CONDITIONS4___
      SET_TO y = FME_CONDITIONAL:DEFAULT_VALUE'@sub(@Value(_ymin),1.2*(1.5/@cos(@pi()*@Value(_xmax)/180))*@sub(@Value(_ymax),@Value(_ymin)))'BOOL_OP;OR;COMPOSITE_TEST;1 OR 2;TEST @Value(_copynum2) = 0;TEST @Value(_copynum2) = 4'@sum(@Value(_ymax),1.2*(1.5/@cos(@pi()*@Value(_xmax)/180))*@sub(@Value(_ymax),@Value(_ymin)))'BOOL_OP;OR;COMPOSITE_TEST;1;TEST @Value(_copynum2) = 1'@sum(@Value(_ymax),1.2*(1.5/@cos(@pi()*@Value(_xmax)/180))*@sub(@Value(_ymax),@Value(_ymin)))'BOOL_OP;OR;COMPOSITE_TEST;1;TEST @Value(_copynum2) = 2'@sub(@Value(_ymin),1.2*(1.5/@cos(@pi()*@Value(_xmax)/180))*@sub(@Value(_ymax),@Value(_ymin)))'FME_NUM_CONDITIONS4___
    -> GeometryRemover_2
GeometryRemover_2
    -> VertexCreator_10
VertexCreator_10
    MEASURE_TYPE = Continuous
    MISSING_VAL_MODE = Compute
    MODE_NAME = Add Point
    XVAL = @Value(x)
    YVAL = @Value(y)
    -> LineBuilder_7
LineBuilder_7
    ACCUM_INPUT_ATTRS = Use Attributes From One Feature
    REMOVE_DUPLICATES = NO
    POLYGON -> FeatureReader_2 [INITIATOR]
FeatureReader_2
    ATTRIBUTES = TOPO-OSM-WMS,"wms_service_name,wms_service_title,wms_service_abstract,wms_layer_name,wms_layer_title,wms_layer_abstract,wms_selected_layers,fme_geometry{0}"
    ATTR_ACCUM_MODE = Only Use Result
    COMBINE_GEOM = Use Result
    DATASET = http://ows.mundialis.de/services/service?
    FEATURETYPES = TOPO-OSM-WMS
    FORMAT = WMS
    INTERACT = Bounding Boxes Intersect
    OUTPUT_FEATURES_DISPLAY = Schema and Data Features
    WMS_MAP_FORMAT = image/png
    WMS_PIPE_DELIM = yes
    WMS_READER_META_ATTRIBUTES = fme_dataset fme_basename
    WMS_SPLIT_REQUEST = no
    WMS_SRS = EPSG:4326
    WMS_TRANSPARENT = no
    WMS_USE_SEARCH_ENVELOPE = NO
    WMS_WMS_LAYER_LIST = "{OpenStreetMap WMS}|{TOPO-OSM-WMS}"
    TOPO-OSM-WMS -> AttributeManager_9
AttributeManager_9
    ATTR_TABLE = SET_TO _order = 1
    -> Sorter_3
BoundsExtractor_2
    XMAX = _xmax
    XMIN = _xmin
    YMAX = _ymax
    YMIN = _ymin
    ZMAX = _zmax
    ZMIN = _zmin
    -> Cloner_10
    -> Cloner_11
    -> Cloner_12
Cloner_11
    COPIES = 16
    COPYATT = _copynum2
    COPY -> AttributeManager_7
AttributeManager_7
    ATTR_TABLE:
      SET_TO x = FME_CONDITIONAL:DEFAULT_VALUE''BOOL_OP;OR;COMPOSITE_TEST;1 OR 2 OR 3 OR 4 OR 5 OR 6;TEST @Value(_copynum2) = 0;TEST @Value(_copynum2) = 4;TEST @Value(_copynum2) = 11;TEST @Value(_copynum2) = 12;TEST @Value(_copynum2) = 15;TEST @Value(_copynum2) = 3'@Value(_xmin)'BOOL_OP;OR;COMPOSITE_TEST;1 OR 2 OR 3 OR 4 OR 5 OR 6;TEST @Value(_copynum2) = 1;TEST @Value(_copynum2) = 9;TEST @Value(_copynum2) = 10;TEST @Value(_copynum2) = 13;TEST @Value(_copynum2) = 14;TEST @Value(_copynum2) = 2'@Value(_xmax)'BOOL_OP;OR;COMPOSITE_TEST;1 OR 2;TEST @Value(_copynum2) = 5;TEST @Value(_copynum2) = 6'@Evaluate(@Value(_xmin)+(@Value(_xmax)-@Value(_xmin))/3)'BOOL_OP;OR;COMPOSITE_TEST;1 OR 2;TEST @Value(_copynum2) = 7;TEST @Value(_copynum2) = 8'@Evaluate(@Value(_xmin)+2*(@Value(_xmax)-@Value(_xmin))/3)'FME_NUM_CONDITIONS5___
      SET_TO y = FME_CONDITIONAL:DEFAULT_VALUE''BOOL_OP;OR;COMPOSITE_TEST;1 OR 2 OR 3 OR 4 OR 5 OR 6;TEST @Value(_copynum2) = 0;TEST @Value(_copynum2) = 4;TEST @Value(_copynum2) = 5;TEST @Value(_copynum2) = 8;TEST @Value(_copynum2) = 1;TEST @Value(_copynum2) = 9'@Value(_ymax)'BOOL_OP;OR;COMPOSITE_TEST;1 OR 2 OR 3 OR 4;TEST @Value(_copynum2) = 3;TEST @Value(_copynum2) = 6;TEST @Value(_copynum2) = 7;TEST @Value(_copynum2) = 2'@Value(_ymin)'BOOL_OP;OR;COMPOSITE_TEST;1 OR 2;TEST @Value(_copynum2) = 10;TEST @Value(_copynum2) = 11'@Evaluate(@Value(_ymax)-(@Value(_ymax)-@Value(_ymin))/4)'BOOL_OP;OR;COMPOSITE_TEST;1 OR 2;TEST @Value(_copynum2) = 12;TEST @Value(_copynum2) = 13'@Evaluate(@Value(_ymax)-(@Value(_ymax)-@Value(_ymin))/2)'BOOL_OP;OR;COMPOSITE_TEST;1 OR 2;TEST @Value(_copynum2) = 14;TEST @Value(_copynum2) = 15'@Evaluate(@Value(_ymax)-3*(@Value(_ymax)-@Value(_ymin))/4)'FME_NUM_CONDITIONS6___
      SET_TO _order = 2
    -> GeometryRemover_3
GeometryRemover_3
    -> VertexCreator_12
VertexCreator_12
    MEASURE_TYPE = Continuous
    MISSING_VAL_MODE = Compute
    MODE_NAME = Add Point
    XVAL = @Value(x)
    YVAL = @Value(y)
    -> LineBuilder_8
LineBuilder_8
    ACCUM_INPUT_ATTRS = Use Attributes From One Feature
    REMOVE_DUPLICATES = No
    LINE -> PDFStyler_23
PDFStyler_23
    COLOR = 1,0,0
    FILL_COLOR = 0.666667,0,0
    FILL_OPACITY = 1.00
    FONT = Arial,18,BOLD
    LINE_CAP_STYLE_PARAM = Butt Cap
    LINE_DASH_PHASE = 0
    LINE_JOIN_STYLE_PARAM = Miter Join
    LINE_MITER_LIMIT = 0.0
    LINE_WIDTH = 2.0
    OPACITY = 1.0
    PDFStyled -> Sorter_2
    PDFStyled -> Sorter_3
    PDFStyled -> Sorter_4
Cloner_10
    COPIES = 5
    COPYATT = _copynum2
    COPY -> AttributeManager_5
AttributeManager_5
    ATTR_TABLE:
      SET_TO x = FME_CONDITIONAL:DEFAULT_VALUE'@sub(@Value(_xmin),0.3*@sub(@Value(_xmax),@Value(_xmin)))'BOOL_OP;OR;COMPOSITE_TEST;1 OR 2;TEST @Value(_copynum2) = 0;TEST @Value(_copynum2) = 4'@sub(@Value(_xmin),0.3*@sub(@Value(_xmax),@Value(_xmin)))'BOOL_OP;OR;COMPOSITE_TEST;1;TEST @Value(_copynum2) = 1'@sum(@Value(_xmax),0.3*@sub(@Value(_xmax),@Value(_xmin)))'BOOL_OP;OR;COMPOSITE_TEST;1;TEST @Value(_copynum2) = 2'@sum(@Value(_xmax),0.3*@sub(@Value(_xmax),@Value(_xmin)))'FME_NUM_CONDITIONS4___
      SET_TO y = FME_CONDITIONAL:DEFAULT_VALUE'@sub(@Value(_ymin),0.3*(1.5/@cos(@pi()*@Value(_xmax)/180))*@sub(@Value(_ymax),@Value(_ymin)))'BOOL_OP;OR;COMPOSITE_TEST;1 OR 2;TEST @Value(_copynum2) = 0;TEST @Value(_copynum2) = 4'@sum(@Value(_ymax),0.3*(1.5/@cos(@pi()*@Value(_xmax)/180))*@sub(@Value(_ymax),@Value(_ymin)))'BOOL_OP;OR;COMPOSITE_TEST;1;TEST @Value(_copynum2) = 1'@sum(@Value(_ymax),0.3*(1.5/@cos(@pi()*@Value(_xmax)/180))*@sub(@Value(_ymax),@Value(_ymin)))'BOOL_OP;OR;COMPOSITE_TEST;1;TEST @Value(_copynum2) = 2'@sub(@Value(_ymin),0.3*(1.5/@cos(@pi()*@Value(_xmax)/180))*@sub(@Value(_ymax),@Value(_ymin)))'FME_NUM_CONDITIONS4___
    -> GeometryRemover
GeometryRemover
    -> VertexCreator
VertexCreator
    MEASURE_TYPE = Continuous
    MISSING_VAL_MODE = Compute
    MODE_NAME = Add Point
    XVAL = @Value(x)
    YVAL = @Value(y)
    -> LineBuilder
LineBuilder
    ACCUM_INPUT_ATTRS = Use Attributes From One Feature
    REMOVE_DUPLICATES = NO
    POLYGON -> FeatureReader_3 [INITIATOR]
FeatureReader_3
    ATTRIBUTES = TOPO-OSM-WMS,"wms_service_name,wms_service_title,wms_service_abstract,wms_layer_name,wms_layer_title,wms_layer_abstract,wms_selected_layers,fme_geometry{0}"
    ATTR_ACCUM_MODE = Only Use Result
    COMBINE_GEOM = Use Result
    DATASET = http://ows.mundialis.de/services/service?
    FEATURETYPES = TOPO-OSM-WMS
    FORMAT = WMS
    INTERACT = Bounding Boxes Intersect
    OUTPUT_FEATURES_DISPLAY = Schema and Data Features
    WMS_MAP_FORMAT = image/png
    WMS_PIPE_DELIM = yes
    WMS_READER_META_ATTRIBUTES = fme_dataset fme_basename
    WMS_SPLIT_REQUEST = no
    WMS_SRS = EPSG:4326
    WMS_TRANSPARENT = no
    WMS_USE_SEARCH_ENVELOPE = NO
    WMS_WMS_LAYER_LIST = "{OpenStreetMap WMS}|{TOPO-OSM-WMS}"
    TOPO-OSM-WMS -> AttributeManager_8
AttributeManager_8
    ATTR_TABLE = SET_TO _order = 1
    -> Sorter_2
Cloner_12
    COPIES = 5
    COPYATT = _copynum2
    COPY -> AttributeManager_11
AttributeManager_11
    ATTR_TABLE:
      SET_TO x = FME_CONDITIONAL:DEFAULT_VALUE''BOOL_OP;COMPOSITE;COMPOSITE_TEST;( 1 OR 2 OR 3 )
         AND 4;TEST @Value(_copynum2) = 0;TEST @Value(_copynum2) = 4;TEST @Value(_copynum2) = 3;TEST $(Tile_num) = 0'@Value(_xmin)'BOOL_OP;COMPOSITE;COMPOSITE_TEST;( 1 OR 2 )
         AND 3;TEST @Value(_copynum2) = 1;TEST @Value(_copynum2) = 2;TEST $(Tile_num) = 0'@Value(_xmax)'BOOL_OP;COMPOSITE;COMPOSITE_TEST;( 1 OR 2 OR 3 )
         AND ( 4 OR 5 OR 6 OR 7 );TEST @Value(_copynum2) = 0;TEST @Value(_copynum2) = 4;TEST @Value(_copynum2) = 3;TEST $(Tile_num) = 1;TEST $(Tile_num) = 4;TEST $(Tile_num) = 7;TEST $(Tile_num) = 10'@Value(_xmin)'BOOL_OP;COMPOSITE;COMPOSITE_TEST;( 1 OR 2 )
         AND ( 3 OR 4 OR 5 OR 6 );TEST @Value(_copynum2) = 1;TEST @Value(_copynum2) = 2;TEST $(Tile_num) = 1;TEST $(Tile_num) = 4;TEST $(Tile_num) = 7;TEST $(Tile_num) = 10'@Evaluate(@Value(_xmin)+(@Value(_xmax)-@Value(_xmin))/3)'BOOL_OP;COMPOSITE;COMPOSITE_TEST;( 1 OR 2 OR 3 )
         AND ( 4 OR 5 OR 6 OR 7 );TEST @Value(_copynum2) = 0;TEST @Value(_copynum2) = 4;TEST @Value(_copynum2) = 3;TEST $(Tile_num) = 2;TEST $(Tile_num) = 5;TEST $(Tile_num) = 8;TEST $(Tile_num) = 11'@Evaluate(@Value(_xmin)+(@Value(_xmax)-@Value(_xmin))/3)'BOOL_OP;COMPOSITE;COMPOSITE_TEST;( 1 OR 2 )
         AND ( 3 OR 4 OR 5 OR 6 );TEST @Value(_copynum2) = 1;TEST @Value(_copynum2) = 2;TEST $(Tile_num) = 2;TEST $(Tile_num) = 5;TEST $(Tile_num) = 8;TEST $(Tile_num) = 11'@Evaluate(@Value(_xmin)+2*(@Value(_xmax)-@Value(_xmin))/3)'BOOL_OP;COMPOSITE;COMPOSITE_TEST;( 1 OR 2 OR 3 )
         AND ( 4 OR 5 OR 6 OR 7 );TEST @Value(_copynum2) = 0;TEST @Value(_copynum2) = 4;TEST @Value(_copynum2) = 3;TEST $(Tile_num) = 3;TEST $(Tile_num) = 6;TEST $(Tile_num) = 9;TEST $(Tile_num) = 12'@Evaluate(@Value(_xmin)+2*(@Value(_xmax)-@Value(_xmin))/3)'BOOL_OP;COMPOSITE;COMPOSITE_TEST;( 1 OR 2 )
         AND ( 3 OR 4 OR 5 OR 6 );TEST @Value(_copynum2) = 1;TEST @Value(_copynum2) = 2;TEST $(Tile_num) = 3;TEST $(Tile_num) = 6;TEST $(Tile_num) = 9;TEST $(Tile_num) = 12'@Value(_xmax)'FME_NUM_CONDITIONS9___
      SET_TO y = FME_CONDITIONAL:DEFAULT_VALUE''BOOL_OP;COMPOSITE;COMPOSITE_TEST;( 1 OR 2 OR 3 )
         AND ( 4 OR 5 OR 6 OR 7 );TEST @Value(_copynum2) = 0;TEST @Value(_copynum2) = 4;TEST @Value(_copynum2) = 1;TEST $(Tile_num) = 0;TEST $(Tile_num) = 1;TEST $(Tile_num) = 2;TEST $(Tile_num) = 3'@Value(_ymax)'BOOL_OP;COMPOSITE;COMPOSITE_TEST;( 1 OR 2 )
         AND ( 3 OR 4 OR 5 OR 6 );TEST @Value(_copynum2) = 2;TEST @Value(_copynum2) = 3;TEST $(Tile_num) = 0;TEST $(Tile_num) = 1;TEST $(Tile_num) = 2;TEST $(Tile_num) = 3'@Evaluate(@Value(_ymax)-(@Value(_ymax)-@Value(_ymin))/4)'BOOL_OP;COMPOSITE;COMPOSITE_TEST;( 1 OR 2 OR 3 )
         AND ( 4 OR 5 OR 6 );TEST @Value(_copynum2) = 0;TEST @Value(_copynum2) = 4;TEST @Value(_copynum2) = 1;TEST $(Tile_num) = 4;TEST $(Tile_num) = 5;TEST $(Tile_num) = 6'@Evaluate(@Value(_ymax)-(@Value(_ymax)-@Value(_ymin))/4)'BOOL_OP;COMPOSITE;COMPOSITE_TEST;( 1 OR 2 )
         AND ( 3 OR 4 OR 5 );TEST @Value(_copynum2) = 2;TEST @Value(_copynum2) = 3;TEST $(Tile_num) = 4;TEST $(Tile_num) = 5;TEST $(Tile_num) = 6'@Evaluate(@Value(_ymax)-(@Value(_ymax)-@Value(_ymin))/2)'BOOL_OP;COMPOSITE;COMPOSITE_TEST;( 1 OR 2 OR 3 )
         AND ( 4 OR 5 OR 6 );TEST @Value(_copynum2) = 0;TEST @Value(_copynum2) = 4;TEST @Value(_copynum2) = 1;TEST $(Tile_num) = 7;TEST $(Tile_num) = 8;TEST $(Tile_num) = 9'@Evaluate(@Value(_ymax)-(@Value(_ymax)-@Value(_ymin))/2)'BOOL_OP;COMPOSITE;COMPOSITE_TEST;( 1 OR 2 )
         AND ( 3 OR 4 OR 5 );TEST @Value(_copynum2) = 2;TEST @Value(_copynum2) = 3;TEST $(Tile_num) = 7;TEST $(Tile_num) = 8;TEST $(Tile_num) = 9'@Evaluate(@Value(_ymax)-3*(@Value(_ymax)-@Value(_ymin))/4)'BOOL_OP;COMPOSITE;COMPOSITE_TEST;( 1 OR 2 OR 3 )
         AND ( 4 OR 5 OR 6 );TEST @Value(_copynum2) = 0;TEST @Value(_copynum2) = 4;TEST @Value(_copynum2) = 1;TEST $(Tile_num) = 10;TEST $(Tile_num) = 11;TEST $(Tile_num) = 12'@Evaluate(@Value(_ymax)-3*(@Value(_ymax)-@Value(_ymin))/4)'BOOL_OP;COMPOSITE;COMPOSITE_TEST;( 1 OR 2 )
         AND ( 3 OR 4 OR 5 );TEST @Value(_copynum2) = 2;TEST @Value(_copynum2) = 3;TEST $(Tile_num) = 10;TEST $(Tile_num) = 11;TEST $(Tile_num) = 12'@Value(_ymin)'FME_NUM_CONDITIONS9___
      SET_TO _order = 3
    -> GeometryRemover_4
GeometryRemover_4
    -> VertexCreator_13
VertexCreator_13
    MEASURE_TYPE = Continuous
    MISSING_VAL_MODE = Compute
    MODE_NAME = Add Point
    XVAL = @Value(x)
    YVAL = @Value(y)
    -> LineBuilder_9
LineBuilder_9
    ACCUM_INPUT_ATTRS = Use Attributes From One Feature
    REMOVE_DUPLICATES = NO
    POLYGON -> PDFStyler_24
PDFStyler_24
    COLOR = 1,0.945098,0.133333
    FILL_COLOR = 0.658824,0.666667,0.160784
    FILL_OPACITY = 0.08
    FONT = Arial,18,BOLD
    LINE_CAP_STYLE_PARAM = Butt Cap
    LINE_DASH_PHASE = 0
    LINE_JOIN_STYLE_PARAM = Miter Join
    LINE_MITER_LIMIT = 0.0
    LINE_WIDTH = 2.0
    OPACITY = 1.0
    PDFStyled -> Sorter_2
    PDFStyled -> Sorter_3
    PDFStyled -> Sorter_4
Note: Sort drawing order with _order
Sorter_4
    SORT_PARM = _order NUMERIC ASCENDING
    SORTED -> PDFPageFormatter_2 [Main]
Note: Sort drawing order with _order
Sorter_3
    SORT_PARM = _order NUMERIC ASCENDING
    SORTED -> PDFPageFormatter_2 [Main3]
Note: Sort drawing order with _order
Sorter_2
    SORT_PARM = _order NUMERIC ASCENDING
    SORTED -> PDFPageFormatter_2 [Main2]
Note: Set the page size and add 'Title', 'Main' and 'Signature' frames. / To control the feature type order in the output 'Layer', they must / be ordered by how they should be drawn using the sorter transformer. / NOTE: All feature types that overlap must be considered in the / same frame (drawing object) or the scale and bounds will not match.
PDFPageFormatter
    PAGE_HEIGHT_PTS = 612
    PAGE_HEIGHT_USER = 8.5
    PAGE_NUMBER = 1
    PAGE_OBJECTS = "PF HEIGHT;25.92;MINY;555.12;SCALING_PARAMS;;FIXED_ASPECT;Yes;CLIPPING_ENABLED;No;SIZE_PARAMS;;MINX;562.32;WIDTH;144.72","Features_preview HEIGHT;63.36;MINY;491.04;SCALING_PARAMS;;FIXED_ASPECT;Yes;CLIPPING_ENABLED;No;SIZE_PARAMS;;MINX;562.32;WIDTH;187.2","Tf HEIGHT;63.36;MINY;492.48;SCALING_PARAMS;;FIXED_ASPECT;Yes;CLIPPING_ENABLED;No;SIZE_PARAMS;;MINX;571.68;WIDTH;193.68","Hide HEIGHT;63.36;MINY;491.04;SCALING_PARAMS;;FIXED_ASPECT;Yes;CLIPPING_ENABLED;No;SIZE_PARAMS;;MINX;562.32;WIDTH;187.2","Units HEIGHT;20.16;MINY;123.84;SCALING_PARAMS;;FIXED_ASPECT;Yes;CLIPPING_ENABLED;No;SIZE_PARAMS;;MINX;587.52;WIDTH;84.24","left_scale HEIGHT;21.6;MINY;104.4;SCALING_PARAMS;;FIXED_ASPECT;Yes;CLIPPING_ENABLED;No;SIZE_PARAMS;;MINX;586.8;WIDTH;68.4","right_scale HEIGHT;21.6;MINY;104.4;SCALING_PARAMS;;FIXED_ASPECT;Yes;CLIPPING_ENABLED;No;SIZE_PARAMS;;MINX;655.92;WIDTH;68.4","Scale 1 HEIGHT;14.4;MINY;87.84;SCALING_PARAMS;;FIXED_ASPECT;Yes;CLIPPING_ENABLED;No;SIZE_PARAMS;;MINX;702;WIDTH;36","Signature_Frame HEIGHT;20;MINY;6.36556;SCALING_PARAMS;;FIXED_ASPECT;Yes;CLIPPING_ENABLED;No;SIZE_PARAMS;;MINX;588.119;WIDTH;198","Title_Frame HEIGHT;20;MINY;578.035;SCALING_PARAMS;;FIXED_ASPECT;Yes;CLIPPING_ENABLED;No;SIZE_PARAMS;;MINX;17.2456;WIDTH;219.47","Main HEIGHT;540;MINY;27.0021;SCALING_PARAMS;;FIXED_ASPECT;Yes;CLIPPING_ENABLED;No;SIZE_PARAMS;;MINX;13.6972;WIDTH;540","Scale 2 HEIGHT;14.4;MINY;87.84;SCALING_PARAMS;;FIXED_ASPECT;Yes;CLIPPING_ENABLED;No;SIZE_PARAMS;;MINX;635.76;WIDTH;36","Scale 3 HEIGHT;14.4;MINY;87.84;SCALING_PARAMS;;FIXED_ASPECT;Yes;CLIPPING_ENABLED;No;SIZE_PARAMS;;MINX;568.08;WIDTH;36","North HEIGHT;14.4;MINY;223.2;SCALING_PARAMS;;FIXED_ASPECT;Yes;CLIPPING_ENABLED;No;SIZE_PARAMS;;MINX;648;WIDTH;14.4","tabular HEIGHT;166.32;MINY;265.68;SCALING_PARAMS;;FIXED_ASPECT;Yes;CLIPPING_ENABLED;No;SIZE_PARAMS;;MINX;587.52;WIDTH;144.72","coord HEIGHT;47.52;MINY;420.48;SCALING_PARAMS;;FIXED_ASPECT;Yes;CLIPPING_ENABLED;No;SIZE_PARAMS;;MINX;594.72;WIDTH;138.96","arrow HEIGHT;52.56;MINY;163.44;SCALING_PARAMS;;FIXED_ASPECT;Yes;CLIPPING_ENABLED;No;SIZE_PARAMS;;MINX;626.4;WIDTH;57.6"
    PAGE_ORIENTATION = Landscape
    PAGE_SIZE = Letter
    PAGE_UNITS = Inches
    PAGE_WIDTH_PTS = 792
    PAGE_WIDTH_USER = 11
    -> JPEG2000 (writer PDF2D_3)
pdf_no_layer (reader PDF2D_2)
    -> AttributeManager_2
AttributeManager_2
    ATTR_TABLE = SET_TO pdf_page_number = FME_CONDITIONAL:DEFAULT_VALUE'_FME_NO_OP_'BOOL_OP;OR;COMPOSITE_TEST;1;TEST @Value(pdf_page_number) = 1'2'BOOL_OP;OR;COMPOSITE_TEST;1;TEST @Value(pdf_page_number) = 2'3'FME_NUM_CONDITIONS3___
    -> JPEG2000 (writer PDF2D_3)
Date: Creator
    GEOM = <?xml version="1.0" encoding="US_ASCII" standalone="no" ?><geometry><text><point><coord x="0" y="0"/></point><textString>null</textString><textSize>1</textSize><textRotation>0</textRotation></text></geometry>
    GEOMTYPE = Geometry Object
    NUM = 1
    CREATED -> AttributeExposer_3
AttributeExposer_3
    ATTR_LIST = fme_text_string
    -> AttributeManager_4
AttributeManager_4
    ATTR_TABLE:
      SET_TO fme_type = fme_text
      SET_TO fme_text_size = 10
      SET_TO fme_feature_type = Scale_center
      SET_TO fme_geometry = fme_point
      SET_TO fme_rotation = 0
      SET_TO fme_text_string = @DateTimeFormat($(DATE),%Y-%m-%d)
    -> PDFStyler_22
PDFStyler_22
    COLOR = 0,0,0
    FILL_COLOR = 0,0,0
    FILL_OPACITY = 1.00
    FONT = Arial,18,BOLD
    LINE_CAP_STYLE_PARAM = Butt Cap
    LINE_DASH_PHASE = 0
    LINE_JOIN_STYLE_PARAM = Miter Join
    LINE_MITER_LIMIT = 0.0
    LINE_WIDTH = 1.0
    OPACITY = 1.0
    PDFStyled -> PDFPageFormatter_2 [date]
Creator_8
    GEOM = <?xml version="1.0" encoding="US_ASCII" standalone="no" ?><geometry><text><point><coord x="0" y="0"/></point><textString>PDF export</textString><textSize>1</textSize><textRotation>0</textRotation></text></geometry>
    GEOMTYPE = Geometry Object
    NUM = 1
    CREATED -> PDFStyler_21
PDFStyler_21
    COLOR = 0,0,0
    FILL_COLOR = 0,0,0
    FILL_OPACITY = 1.00
    FONT = Arial,18,BOLD
    LINE_CAP_STYLE_PARAM = Butt Cap
    LINE_DASH_PHASE = 0
    LINE_JOIN_STYLE_PARAM = Miter Join
    LINE_MITER_LIMIT = 0.0
    LINE_WIDTH = 1.0
    OPACITY = 1.0
    PDFStyled -> PDFPageFormatter_2 [Title]
Note: Set the page size and add 'Title', 'Main' and 'Signature' frames. / To control the feature type order in the output 'Layer', they must / be ordered by how they should be drawn using the sorter transformer. / NOTE: All feature types that overlap must be considered in the / same frame (drawing object) or the scale and bounds will not match.
PDFPageFormatter_2
    PAGE_HEIGHT_PTS = 612
    PAGE_HEIGHT_USER = 8.5
    PAGE_NUMBER = 4
    PAGE_OBJECTS = "date FIXED_ASPECT;Yes;WIDTH;108;MINY;511.2;CLIPPING_ENABLED;No;HEIGHT;36;MINX;129.6;SIZE_PARAMS;;SCALING_PARAMS;","signature FIXED_ASPECT;Yes;WIDTH;215.09;MINY;11.8754;CLIPPING_ENABLED;No;HEIGHT;32.1;MINX;559.407;SIZE_PARAMS;;SCALING_PARAMS;","header FIXED_ASPECT;Yes;WIDTH;280.24;MINY;564.574;CLIPPING_ENABLED;No;HEIGHT;37.72;MINX;11.8564;SIZE_PARAMS;;SCALING_PARAMS;","Title FIXED_ASPECT;Yes;WIDTH;108;MINY;511.2;CLIPPING_ENABLED;No;HEIGHT;36;MINX;14.4;SIZE_PARAMS;;SCALING_PARAMS;","Main2 FIXED_ASPECT;Yes;WIDTH;252.22;MINY;259.782;CLIPPING_ENABLED;No;HEIGHT;231.5;MINX;94.8517;SIZE_PARAMS;;SCALING_PARAMS;","Main3 FIXED_ASPECT;Yes;WIDTH;229.58;MINY;261.698;CLIPPING_ENABLED;No;HEIGHT;226.35;MINX;396.65;SIZE_PARAMS;;SCALING_PARAMS;","Main FIXED_ASPECT;Yes;WIDTH;238.52;MINY;8.401;CLIPPING_ENABLED;No;HEIGHT;232.01;MINX;247.592;SIZE_PARAMS;;SCALING_PARAMS;"
    PAGE_ORIENTATION = Landscape
    PAGE_SIZE = Letter
    PAGE_UNITS = Inches
    PAGE_WIDTH_PTS = 792
    PAGE_WIDTH_USER = 11
    -> JPEG2000 (writer PDF2D_3)
JPEG2000 (writer PDF2D_3)

Bookmark: BaseMap & Frame
AttributeCreator
    ATTR_TABLE:
      SET_TO _order = 0
      SET_TO fme_feature_type = BackgroundMap
    -> Sorter
AttributeCreator_2
    ATTR_TABLE:
      SET_TO _order = 1
      SET_TO fme_feature_type = BoundingBox
    -> PDFStyler_3
PDFStyler_3
    COLOR = 0,0,0
    FILL_COLOR = 0,0,0
    FILL_OPACITY = 0
    FONT = Helvetica,9
    LINE_CAP_STYLE_PARAM = Butt Cap
    LINE_DASH_PHASE = 0
    LINE_JOIN_STYLE_PARAM = Miter Join
    LINE_MITER_LIMIT = 0.0
    LINE_WIDTH = 3
    OPACITY = 1.0
    PDFStyled -> Sorter

Bookmark: Printed features preview
Creator_7
    GEOMTYPE = Geometry Object
    NUM = 5
    CREATED -> Cloner_3
Cloner_3
    COPIES = 7
    COPYATT = _offset
    COPY -> Cloner_7
Cloner_7
    COPIES = 4
    COPYATT = _offset_y
    COPY -> VertexCreator_4
VertexCreator_4
    MEASURE_TYPE = Continuous
    MISSING_VAL_MODE = Compute
    MODE_NAME = Add Point
    XVAL = FME_CONDITIONAL:DEFAULT_VALUE''BOOL_OP;OR;COMPOSITE_TEST;1 OR 2;TEST @Value(_creation_instance) = 0;TEST @Value(_creation_instance) = 4'0 + 4*@Value(_offset)'BOOL_OP;OR;COMPOSITE_TEST;1;TEST @Value(_creation_instance) = 1'1 + 4*@Value(_offset)'BOOL_OP;OR;COMPOSITE_TEST;1;TEST @Value(_creation_instance) = 2'1 + 4*@Value(_offset)'BOOL_OP;OR;COMPOSITE_TEST;1;TEST @Value(_creation_instance) = 3'0 + 4*@Value(_offset)'FME_NUM_CONDITIONS5___
    YVAL = FME_CONDITIONAL:DEFAULT_VALUE''BOOL_OP;OR;COMPOSITE_TEST;1 OR 2;TEST @Value(_creation_instance) = 0;TEST @Value(_creation_instance) = 4'1 + 2*@Value(_offset_y)'BOOL_OP;OR;COMPOSITE_TEST;1;TEST @Value(_creation_instance) = 1'1 + 2*@Value(_offset_y)'BOOL_OP;OR;COMPOSITE_TEST;1;TEST @Value(_creation_instance) = 2'0  + 2*@Value(_offset_y)'BOOL_OP;OR;COMPOSITE_TEST;1;TEST @Value(_creation_instance) = 3'0  + 2*@Value(_offset_y)'FME_NUM_CONDITIONS5___
    -> TestFilter_5
TestFilter_5
    DEFAULT_VALUE = pass
    TEST_LIST:
      "BOOL_OP,COMPOSITE,COMPOSITE_TEST,""""""1 AND ( 2 OR 3 ) AND ( 4 )"""""",TEST_CLAUSE,TEST @Value(_creation_instance) = 0
      TEST @Value(_offset) = 6
      TEST @Value(_offset) = 5
      TEST @Value(_offset_y) = 0",delete,"BOOL_OP,AND,COMPOSITE_TEST,""""""1 AND 2 AND 3 AND 4"""""",TEST_CLAUSE,CASE_INSENSITIVE_TEST $(Features_to_print) CONTAINS aerialway
      CASE_INSENSITIVE_TEST @Value(_creation_instance) = 4
      CASE_INSENSITIVE_TEST @Value(_offset) = 0
      CASE_INSENSITIVE_TEST @Value(_offset_y) = 3",delete,"BOOL_OP,AND,COMPOSITE_TEST,""""""1 AND 2 AND 3 AND 4"""""",TEST_CLAUSE,CASE_INSENSITIVE_TEST $(Features_to_print) CONTAINS aeroway
      CASE_INSENSITIVE_TEST @Value(_creation_instance) = 4
      CASE_INSENSITIVE_TEST @Value(_offset) = 1
      CASE_INSENSITIVE_TEST @Value(_offset_y) = 3",delete,"BOOL_OP,AND,COMPOSITE_TEST,""""""1 AND 2 AND 3 AND 4"""""",TEST_CLAUSE,CASE_INSENSITIVE_TEST $(Features_to_print) CONTAINS amenity
      CASE_INSENSITIVE_TEST @Value(_creation_instance) = 4
      CASE_INSENSITIVE_TEST @Value(_offset) = 2
      CASE_INSENSITIVE_TEST @Value(_offset_y) = 3",delete,"BOOL_OP,AND,COMPOSITE_TEST,""""""1 AND 2 AND 3 AND 4"""""",TEST_CLAUSE,CASE_INSENSITIVE_TEST $(Features_to_print) CONTAINS barrier
      CASE_INSENSITIVE_TEST @Value(_creation_instance) = 4
      CASE_INSENSITIVE_TEST @Value(_offset) = 3
      CASE_INSENSITIVE_TEST @Value(_offset_y) = 3",delete,"BOOL_OP,AND,COMPOSITE_TEST,""""""1 AND 2 AND 3 AND 4"""""",TEST_CLAUSE,CASE_INSENSITIVE_TEST $(Features_to_print) CONTAINS boundary
      CASE_INSENSITIVE_TEST @Value(_creation_instance) = 4
      CASE_INSENSITIVE_TEST @Value(_offset) = 4
      CASE_INSENSITIVE_TEST @Value(_offset_y) = 3",delete,"BOOL_OP,AND,COMPOSITE_TEST,""""""1 AND 2 AND 3 AND 4"""""",TEST_CLAUSE,CASE_INSENSITIVE_TEST $(Features_to_print) CONTAINS building
      CASE_INSENSITIVE_TEST @Value(_creation_instance) = 4
      CASE_INSENSITIVE_TEST @Value(_offset) = 5
      CASE_INSENSITIVE_TEST @Value(_offset_y) = 3",delete,"BOOL_OP,AND,COMPOSITE_TEST,""""""1 AND 2 AND 3 AND 4"""""",TEST_CLAUSE,CASE_INSENSITIVE_TEST $(Features_to_print) CONTAINS craft
      CASE_INSENSITIVE_TEST @Value(_creation_instance) = 4
      CASE_INSENSITIVE_TEST @Value(_offset) = 6
      CASE_INSENSITIVE_TEST @Value(_offset_y) = 3",delete,"BOOL_OP,AND,COMPOSITE_TEST,""""""1 AND 2 AND 3 AND 4"""""",TEST_CLAUSE,CASE_INSENSITIVE_TEST $(Features_to_print) CONTAINS emergency
      CASE_INSENSITIVE_TEST @Value(_creation_instance) = 4
      CASE_INSENSITIVE_TEST @Value(_offset) = 0
      CASE_INSENSITIVE_TEST @Value(_offset_y) = 2",delete,"BOOL_OP,AND,COMPOSITE_TEST,""""""1 AND 2 AND 3 AND 4"""""",TEST_CLAUSE,CASE_INSENSITIVE_TEST $(Features_to_print) CONTAINS geological
      CASE_INSENSITIVE_TEST @Value(_creation_instance) = 4
      CASE_INSENSITIVE_TEST @Value(_offset) = 1
      CASE_INSENSITIVE_TEST @Value(_offset_y) = 2",delete,"BOOL_OP,AND,COMPOSITE_TEST,""""""1 AND 2 AND 3 AND 4"""""",TEST_CLAUSE,CASE_INSENSITIVE_TEST $(Features_to_print) CONTAINS highway
      CASE_INSENSITIVE_TEST @Value(_creation_instance) = 4
      CASE_INSENSITIVE_TEST @Value(_offset) = 2
      CASE_INSENSITIVE_TEST @Value(_offset_y) = 2",delete,"BOOL_OP,AND,COMPOSITE_TEST,""""""1 AND 2 AND 3 AND 4"""""",TEST_CLAUSE,CASE_INSENSITIVE_TEST $(Features_to_print) CONTAINS historic
      CASE_INSENSITIVE_TEST @Value(_creation_instance) = 4
      CASE_INSENSITIVE_TEST @Value(_offset) = 3
      CASE_INSENSITIVE_TEST @Value(_offset_y) = 2",delete,"BOOL_OP,AND,COMPOSITE_TEST,""""""1 AND 2 AND 3 AND 4"""""",TEST_CLAUSE,CASE_INSENSITIVE_TEST $(Features_to_print) CONTAINS landuse
      CASE_INSENSITIVE_TEST @Value(_creation_instance) = 4
      CASE_INSENSITIVE_TEST @Value(_offset) = 4
      CASE_INSENSITIVE_TEST @Value(_offset_y) = 2",delete,"BOOL_OP,AND,COMPOSITE_TEST,""""""1 AND 2 AND 3 AND 4"""""",TEST_CLAUSE,CASE_INSENSITIVE_TEST $(Features_to_print) CONTAINS leisure
      CASE_INSENSITIVE_TEST @Value(_creation_instance) = 4
      CASE_INSENSITIVE_TEST @Value(_offset) = 5
      CASE_INSENSITIVE_TEST @Value(_offset_y) = 2",delete,"BOOL_OP,AND,COMPOSITE_TEST,""""""1 AND 2 AND 3 AND 4"""""",TEST_CLAUSE,CASE_INSENSITIVE_TEST $(Features_to_print) CONTAINS man_made
      CASE_INSENSITIVE_TEST @Value(_creation_instance) = 4
      CASE_INSENSITIVE_TEST @Value(_offset) = 6
      CASE_INSENSITIVE_TEST @Value(_offset_y) = 2",delete,"BOOL_OP,AND,COMPOSITE_TEST,""""""1 AND 2 AND 3 AND 4"""""",TEST_CLAUSE,CASE_INSENSITIVE_TEST $(Features_to_print) CONTAINS military
      CASE_INSENSITIVE_TEST @Value(_creation_instance) = 4
      CASE_INSENSITIVE_TEST @Value(_offset) = 0
      CASE_INSENSITIVE_TEST @Value(_offset_y) = 1",delete,"BOOL_OP,AND,COMPOSITE_TEST,""""""1 AND 2 AND 3 AND 4"""""",TEST_CLAUSE,CASE_INSENSITIVE_TEST $(Features_to_print) CONTAINS natural
      CASE_INSENSITIVE_TEST @Value(_creation_instance) = 4
      CASE_INSENSITIVE_TEST @Value(_offset) = 1
      CASE_INSENSITIVE_TEST @Value(_offset_y) = 1",delete,"BOOL_OP,AND,COMPOSITE_TEST,""""""1 AND 2 AND 3 AND 4"""""",TEST_CLAUSE,CASE_INSENSITIVE_TEST $(Features_to_print) CONTAINS office
      CASE_INSENSITIVE_TEST @Value(_creation_instance) = 4
      CASE_INSENSITIVE_TEST @Value(_offset) = 2
      CASE_INSENSITIVE_TEST @Value(_offset_y) = 1",delete,"BOOL_OP,AND,COMPOSITE_TEST,""""""1 AND 2 AND 3 AND 4"""""",TEST_CLAUSE,CASE_INSENSITIVE_TEST $(Features_to_print) CONTAINS place
      CASE_INSENSITIVE_TEST @Value(_creation_instance) = 4
      CASE_INSENSITIVE_TEST @Value(_offset) = 3
      CASE_INSENSITIVE_TEST @Value(_offset_y) = 1",delete,"BOOL_OP,AND,COMPOSITE_TEST,""""""1 AND 2 AND 3 AND 4"""""",TEST_CLAUSE,CASE_INSENSITIVE_TEST $(Features_to_print) CONTAINS power
      CASE_INSENSITIVE_TEST @Value(_creation_instance) = 4
      CASE_INSENSITIVE_TEST @Value(_offset) = 4
      CASE_INSENSITIVE_TEST @Value(_offset_y) = 1",delete,"BOOL_OP,AND,COMPOSITE_TEST,""""""1 AND 2 AND 3 AND 4"""""",TEST_CLAUSE,CASE_INSENSITIVE_TEST $(Features_to_print) CONTAINS power
      CASE_INSENSITIVE_TEST @Value(_creation_instance) = 4
      CASE_INSENSITIVE_TEST @Value(_offset) = 5
      CASE_INSENSITIVE_TEST @Value(_offset_y) = 1",delete,"BOOL_OP,AND,COMPOSITE_TEST,""""""1 AND 2 AND 3 AND 4"""""",TEST_CLAUSE,CASE_INSENSITIVE_TEST $(Features_to_print) CONTAINS public_transport
      CASE_INSENSITIVE_TEST @Value(_creation_instance) = 4
      CASE_INSENSITIVE_TEST @Value(_offset) = 5
      CASE_INSENSITIVE_TEST @Value(_offset_y) = 1",delete,"BOOL_OP,AND,COMPOSITE_TEST,""""""1 AND 2 AND 3 AND 4"""""",TEST_CLAUSE,CASE_INSENSITIVE_TEST $(Features_to_print) CONTAINS railway
      CASE_INSENSITIVE_TEST @Value(_creation_instance) = 4
      CASE_INSENSITIVE_TEST @Value(_offset) = 6
      CASE_INSENSITIVE_TEST @Value(_offset_y) = 1",delete,"BOOL_OP,AND,COMPOSITE_TEST,""""""1 AND 2 AND 3 AND 4"""""",TEST_CLAUSE,CASE_INSENSITIVE_TEST $(Features_to_print) CONTAINS route
      CASE_INSENSITIVE_TEST @Value(_creation_instance) = 4
      CASE_INSENSITIVE_TEST @Value(_offset) = 0
      CASE_INSENSITIVE_TEST @Value(_offset_y) = 0",delete,"BOOL_OP,AND,COMPOSITE_TEST,""""""1 AND 2 AND 3 AND 4"""""",TEST_CLAUSE,CASE_INSENSITIVE_TEST $(Features_to_print) CONTAINS shop
      CASE_INSENSITIVE_TEST @Value(_creation_instance) = 4
      CASE_INSENSITIVE_TEST @Value(_offset) = 1
      CASE_INSENSITIVE_TEST @Value(_offset_y) = 0",delete,"BOOL_OP,AND,COMPOSITE_TEST,""""""1 AND 2 AND 3 AND 4"""""",TEST_CLAUSE,CASE_INSENSITIVE_TEST $(Features_to_print) CONTAINS sport
      CASE_INSENSITIVE_TEST @Value(_creation_instance) = 4
      CASE_INSENSITIVE_TEST @Value(_offset) = 2
      CASE_INSENSITIVE_TEST @Value(_offset_y) = 0",delete,"BOOL_OP,AND,COMPOSITE_TEST,""""""1 AND 2 AND 3 AND 4"""""",TEST_CLAUSE,CASE_INSENSITIVE_TEST $(Features_to_print) CONTAINS tourism
      CASE_INSENSITIVE_TEST @Value(_creation_instance) = 4
      CASE_INSENSITIVE_TEST @Value(_offset) = 3
      CASE_INSENSITIVE_TEST @Value(_offset_y) = 0",delete,"BOOL_OP,AND,COMPOSITE_TEST,""""""1 AND 2 AND 3 AND 4"""""",TEST_CLAUSE,CASE_INSENSITIVE_TEST $(Features_to_print) CONTAINS waterway
      CASE_INSENSITIVE_TEST @Value(_creation_instance) = 4
      CASE_INSENSITIVE_TEST @Value(_offset) = 4
      CASE_INSENSITIVE_TEST @Value(_offset_y) = 0",delete
    pass -> LineBuilder_3
LineBuilder_3
    ACCUM_INPUT_ATTRS = Use Attributes From One Feature
    GROUP_BY = _offset _offset_y
    REMOVE_DUPLICATES = No
    POLYGON -> PDFStyler_8
PDFStyler_8
    COLOR = 0,0,0
    FILL_COLOR = 1,1,1
    FILL_OPACITY = 1.00
    FONT = MS Shell Dlg 2,12,BOLD
    LINE_CAP_STYLE_PARAM = Butt Cap
    LINE_DASH_PHASE = 0
    LINE_JOIN_STYLE_PARAM = Miter Join
    LINE_MITER_LIMIT = 0.0
    LINE_WIDTH = 1
    OPACITY = 1.0
    PDFStyled -> PDFPageFormatter [Hide]
Creator_6
    GEOMTYPE = Geometry Object
    NUM = 8
    CREATED -> Cloner_4
Cloner_4
    COPIES = 7
    COPYATT = _offset
    COPY -> Cloner_2
Cloner_2
    COPIES = 4
    COPYATT = _offset_y
    COPY -> VertexCreator_2
VertexCreator_2
    MEASURE_TYPE = Continuous
    MISSING_VAL_MODE = Compute
    MODE_NAME = Add Point
    XVAL = FME_CONDITIONAL:DEFAULT_VALUE''BOOL_OP;OR;COMPOSITE_TEST;1 OR 2;TEST @Value(_creation_instance) = 0;TEST @Value(_creation_instance) = 4'0 + 4*@Value(_offset)'BOOL_OP;OR;COMPOSITE_TEST;1;TEST @Value(_creation_instance) = 1'1 + 4*@Value(_offset)'BOOL_OP;OR;COMPOSITE_TEST;1;TEST @Value(_creation_instance) = 2'1 + 4*@Value(_offset)'BOOL_OP;OR;COMPOSITE_TEST;1;TEST @Value(_creation_instance) = 3'0 + 4*@Value(_offset)'BOOL_OP;OR;COMPOSITE_TEST;1;TEST @Value(_creation_instance) = 5'1 +  4*@Value(_offset)'BOOL_OP;OR;COMPOSITE_TEST;1;TEST @Value(_creation_instance) = 6'0 + 4* @Value(_offset)'BOOL_OP;OR;COMPOSITE_TEST;1;TEST @Value(_creation_instance) = 7'1 + 4* @Value(_offset)'FME_NUM_CONDITIONS8___
    YVAL = FME_CONDITIONAL:DEFAULT_VALUE''BOOL_OP;OR;COMPOSITE_TEST;1 OR 2;TEST @Value(_creation_instance) = 0;TEST @Value(_creation_instance) = 4'1 + 2*@Value(_offset_y)'BOOL_OP;OR;COMPOSITE_TEST;1;TEST @Value(_creation_instance) = 1'1 + 2*@Value(_offset_y)'BOOL_OP;OR;COMPOSITE_TEST;1;TEST @Value(_creation_instance) = 2'0  + 2*@Value(_offset_y)'BOOL_OP;OR;COMPOSITE_TEST;1;TEST @Value(_creation_instance) = 3'0  + 2*@Value(_offset_y)'BOOL_OP;OR;COMPOSITE_TEST;1;TEST @Value(_creation_instance) = 5'0  + 2*@Value(_offset_y)'BOOL_OP;OR;COMPOSITE_TEST;1;TEST @Value(_creation_instance) = 6'0  + 2*@Value(_offset_y)'BOOL_OP;OR;COMPOSITE_TEST;1;TEST @Value(_creation_instance) = 7'1  + 2*@Value(_offset_y)'FME_NUM_CONDITIONS8___
    -> TestFilter_4
TestFilter_4
    DEFAULT_VALUE = pass
    TEST_LIST:
      "BOOL_OP,COMPOSITE,COMPOSITE_TEST,""""""1 AND ( 2 OR 3 ) AND ( 4 )"""""",TEST_CLAUSE,TEST @Value(_creation_instance) = 0
      TEST @Value(_offset) = 6
      TEST @Value(_offset) = 5
      TEST @Value(_offset_y) = 0",delete
    pass -> LineBuilder_2
LineBuilder_2
    ACCUM_INPUT_ATTRS = Use Attributes From One Feature
    GROUP_BY = _offset _offset_y
    REMOVE_DUPLICATES = No
    LINE -> PDFStyler_4
PDFStyler_4
    COLOR = 0,0,0
    FILL_COLOR = 0,0.333333,1
    FILL_OPACITY = 0.00
    FONT = MS Shell Dlg 2,12,BOLD
    LINE_CAP_STYLE_PARAM = Butt Cap
    LINE_DASH_PHASE = 0
    LINE_JOIN_STYLE_PARAM = Miter Join
    LINE_MITER_LIMIT = 0.0
    LINE_WIDTH = 1
    OPACITY = 1.0
    PDFStyled -> PDFPageFormatter [Features_preview]
North_3: Creator
    GEOM = <?xml version="1.0" encoding="US_ASCII" standalone="no" ?><geometry><text><point><coord x="0" y="0"/></point><textString>Am</textString><textSize>10</textSize><textRotation>0</textRotation></text></geometry>
    GEOMTYPE = Geometry Object
    NUM = 26
    CREATED -> AttributeManager_3
AttributeManager_3
    ATTR_TABLE:
      SET_TO fme_text_string = FME_CONDITIONAL:DEFAULT_VALUE'_FME_NO_OP_'BOOL_OP;OR;COMPOSITE_TEST;1;TEST @Value(_creation_instance) = 0'Ai'BOOL_OP;OR;COMPOSITE_TEST;1;TEST @Value(_creation_instance) = 1'Ao'BOOL_OP;OR;COMPOSITE_TEST;1;TEST @Value(_creation_instance) = 2'Ae'BOOL_OP;OR;COMPOSITE_TEST;1;TEST @Value(_creation_instance) = 3'Ba'BOOL_OP;OR;COMPOSITE_TEST;1;TEST @Value(_creation_instance) = 4'Bo'BOOL_OP;OR;COMPOSITE_TEST;1;TEST @Value(_creation_instance) = 5'Bu'BOOL_OP;OR;COMPOSITE_TEST;1;TEST @Value(_creation_instance) = 6'Ca'BOOL_OP;OR;COMPOSITE_TEST;1;TEST @Value(_creation_instance) = 7'Em'BOOL_OP;OR;COMPOSITE_TEST;1;TEST @Value(_creation_instance) = 8'Ge'BOOL_OP;OR;COMPOSITE_TEST;1;TEST @Value(_creation_instance) = 9'Hg'BOOL_OP;OR;COMPOSITE_TEST;1;TEST @Value(_creation_instance) = 10'Ht'BOOL_OP;OR;COMPOSITE_TEST;1;TEST @Value(_creation_instance) = 11'La'BOOL_OP;OR;COMPOSITE_TEST;1;TEST @Value(_creation_instance) = 12'Le'BOOL_OP;OR;COMPOSITE_TEST;1;TEST @Value(_creation_instance) = 13'Mm'BOOL_OP;OR;COMPOSITE_TEST;1;TEST @Value(_creation_instance) = 14'Mi'BOOL_OP;OR;COMPOSITE_TEST;1;TEST @Value(_creation_instance) = 15'Na'BOOL_OP;OR;COMPOSITE_TEST;1;TEST @Value(_creation_instance) = 16'Of'BOOL_OP;OR;COMPOSITE_TEST;1;TEST @Value(_creation_instance) = 17'Pl'BOOL_OP;OR;COMPOSITE_TEST;1;TEST @Value(_creation_instance) = 18'Po'BOOL_OP;OR;COMPOSITE_TEST;1;TEST @Value(_creation_instance) = 19'Pt'BOOL_OP;OR;COMPOSITE_TEST;1;TEST @Value(_creation_instance) = 20'Ra'BOOL_OP;OR;COMPOSITE_TEST;1;TEST @Value(_creation_instance) = 21'Ro'BOOL_OP;OR;COMPOSITE_TEST;1;TEST @Value(_creation_instance) = 22'Sh'BOOL_OP;OR;COMPOSITE_TEST;1;TEST @Value(_creation_instance) = 23'Sp'BOOL_OP;OR;COMPOSITE_TEST;1;TEST @Value(_creation_instance) = 24'To'BOOL_OP;OR;COMPOSITE_TEST;1;TEST @Value(_creation_instance) = 25'Wa'FME_NUM_CONDITIONS27___
      SET_TO offset_y = FME_CONDITIONAL:DEFAULT_VALUE'_FME_NO_OP_'BOOL_OP;OR;COMPOSITE_TEST;1;NUM_TEST @Value(_creation_instance) RANGE [0,6]'0'BOOL_OP;OR;COMPOSITE_TEST;1;NUM_TEST @Value(_creation_instance) RANGE [7,13]'1'BOOL_OP;OR;COMPOSITE_TEST;1;NUM_TEST @Value(_creation_instance) RANGE [14,20]'2'BOOL_OP;OR;COMPOSITE_TEST;1;NUM_TEST @Value(_creation_instance) RANGE [21,26]'3'FME_NUM_CONDITIONS5___
      SET_TO offset_x = FME_CONDITIONAL:DEFAULT_VALUE'_FME_NO_OP_'BOOL_OP;OR;COMPOSITE_TEST;1;TEST @Value(_creation_instance) = 0'0'BOOL_OP;OR;COMPOSITE_TEST;1;TEST @Value(_creation_instance) = 7'0'BOOL_OP;OR;COMPOSITE_TEST;1;TEST @Value(_creation_instance) = 14'0'BOOL_OP;OR;COMPOSITE_TEST;1;TEST @Value(_creation_instance) = 21'0'BOOL_OP;OR;COMPOSITE_TEST;1;TEST @Value(_creation_instance) = 1'1'BOOL_OP;OR;COMPOSITE_TEST;1;TEST @Value(_creation_instance) = 8'1'BOOL_OP;OR;COMPOSITE_TEST;1;TEST @Value(_creation_instance) = 15'1'BOOL_OP;OR;COMPOSITE_TEST;1;TEST @Value(_creation_instance) = 22'1'BOOL_OP;OR;COMPOSITE_TEST;1;TEST @Value(_creation_instance) = 2'2'BOOL_OP;OR;COMPOSITE_TEST;1;TEST @Value(_creation_instance) = 9'2'BOOL_OP;OR;COMPOSITE_TEST;1;TEST @Value(_creation_instance) = 16'2'BOOL_OP;OR;COMPOSITE_TEST;1;TEST @Value(_creation_instance) = 23'2'BOOL_OP;OR;COMPOSITE_TEST;1;TEST @Value(_creation_instance) = 3'3'BOOL_OP;OR;COMPOSITE_TEST;1;TEST @Value(_creation_instance) = 10'3'BOOL_OP;OR;COMPOSITE_TEST;1;TEST @Value(_creation_instance) = 17'3'BOOL_OP;OR;COMPOSITE_TEST;1;TEST @Value(_creation_instance) = 24'3'BOOL_OP;OR;COMPOSITE_TEST;1;TEST @Value(_creation_instance) = 4'4'BOOL_OP;OR;COMPOSITE_TEST;1;TEST @Value(_creation_instance) = 11'4'BOOL_OP;OR;COMPOSITE_TEST;1;TEST @Value(_creation_instance) = 18'4'BOOL_OP;OR;COMPOSITE_TEST;1;TEST @Value(_creation_instance) = 25'4'BOOL_OP;OR;COMPOSITE_TEST;1;TEST @Value(_creation_instance) = 5'5'BOOL_OP;OR;COMPOSITE_TEST;1;TEST @Value(_creation_instance) = 12'5'BOOL_OP;OR;COMPOSITE_TEST;1;TEST @Value(_creation_instance) = 19'5'BOOL_OP;OR;COMPOSITE_TEST;1;TEST @Value(_creation_instance) = 26'5'BOOL_OP;OR;COMPOSITE_TEST;1;TEST @Value(_creation_instance) = 6'6'BOOL_OP;OR;COMPOSITE_TEST;1;TEST @Value(_creation_instance) = 13'6'BOOL_OP;OR;COMPOSITE_TEST;1;TEST @Value(_creation_instance) = 20'6'FME_NUM_CONDITIONS28___
    -> Offsetter
Offsetter
    MODE = Cartesian Coordinate
    XOFF = 30 * @Value(offset_x)
    YOFF = - 14.42 * @Value(offset_y)
    ZOFF = 0
    OFFSET -> PDFStyler_5
PDFStyler_5
    COLOR = 0,0,0
    FILL_COLOR = 0,0,0
    FILL_OPACITY = 1.00
    FONT = MS Shell Dlg 2,12,BOLD
    LINE_CAP_STYLE_PARAM = Butt Cap
    LINE_DASH_PHASE = 0
    LINE_JOIN_STYLE_PARAM = Miter Join
    LINE_MITER_LIMIT = 0.0
    LINE_WIDTH = 1.0
    OPACITY = 1.0
    PDFStyled -> PDFPageFormatter [Tf]
North_4: Creator
    GEOM = <?xml version="1.0" encoding="US_ASCII" standalone="no" ?><geometry><text><point><coord x="0" y="0"/></point><textString>Printed features:</textString><textSize>10</textSize><textRotation>0</textRotation></text></geometry>
    GEOMTYPE = Geometry Object
    NUM = 1
    CREATED -> PDFStyler_19
PDFStyler_19
    COLOR = 0,0,0
    FILL_COLOR = 0,0,0
    FILL_OPACITY = 1.00
    FONT = MS Shell Dlg 2,12
    LINE_CAP_STYLE_PARAM = Butt Cap
    LINE_DASH_PHASE = 0
    LINE_JOIN_STYLE_PARAM = Miter Join
    LINE_MITER_LIMIT = 0.0
    LINE_WIDTH = 1.0
    OPACITY = 1.0
    PDFStyled -> PDFPageFormatter [PF]

Bookmark: Tabular subtiles
Creator_2
    GEOMTYPE = Geometry Object
    NUM = 1
    CREATED -> AttributeManager_22
AttributeManager_22
    ATTR_TABLE = SET_TO BB_loc = $(Tile_num)
    -> VertexCreator_6
    -> VertexCreator_7
    -> VertexCreator_8
    -> VertexCreator_11
    -> VertexCreator_9
VertexCreator_6
    MEASURE_TYPE = Continuous
    MISSING_VAL_MODE = Compute
    MODE_NAME = Add Point
    XVAL = FME_CONDITIONAL:DEFAULT_VALUE''BOOL_OP;OR;COMPOSITE_TEST;1;TEST @Value(BB_loc) = 0'0'BOOL_OP;OR;COMPOSITE_TEST;1;TEST @Value(BB_loc) = 1'0'BOOL_OP;OR;COMPOSITE_TEST;1;TEST @Value(BB_loc) = 2'1'BOOL_OP;OR;COMPOSITE_TEST;1;TEST @Value(BB_loc) = 3'2'BOOL_OP;OR;COMPOSITE_TEST;1;TEST @Value(BB_loc) = 4'0'BOOL_OP;OR;COMPOSITE_TEST;1;TEST @Value(BB_loc) = 5'1'BOOL_OP;OR;COMPOSITE_TEST;1;TEST @Value(BB_loc) = 6'2'BOOL_OP;OR;COMPOSITE_TEST;1;TEST @Value(BB_loc) = 7'0'BOOL_OP;OR;COMPOSITE_TEST;1;TEST @Value(BB_loc) = 8'1'BOOL_OP;OR;COMPOSITE_TEST;1;TEST @Value(BB_loc) = 9'2'BOOL_OP;OR;COMPOSITE_TEST;1;TEST @Value(BB_loc) = 10'0'BOOL_OP;OR;COMPOSITE_TEST;1;TEST @Value(BB_loc) = 11'1'BOOL_OP;OR;COMPOSITE_TEST;1;TEST @Value(BB_loc) = 12'2'FME_NUM_CONDITIONS14___
    YVAL = FME_CONDITIONAL:DEFAULT_VALUE''BOOL_OP;OR;COMPOSITE_TEST;1;TEST @Value(BB_loc) = 0'4'BOOL_OP;OR;COMPOSITE_TEST;1;TEST @Value(BB_loc) = 1'4'BOOL_OP;OR;COMPOSITE_TEST;1;TEST @Value(BB_loc) = 2'4'BOOL_OP;OR;COMPOSITE_TEST;1;TEST @Value(BB_loc) = 3'4'BOOL_OP;OR;COMPOSITE_TEST;1;TEST @Value(BB_loc) = 4'3'BOOL_OP;OR;COMPOSITE_TEST;1;TEST @Value(BB_loc) = 5'3'BOOL_OP;OR;COMPOSITE_TEST;1;TEST @Value(BB_loc) = 6'3'BOOL_OP;OR;COMPOSITE_TEST;1;TEST @Value(BB_loc) = 7'2'BOOL_OP;OR;COMPOSITE_TEST;1;TEST @Value(BB_loc) = 8'2'BOOL_OP;OR;COMPOSITE_TEST;1;TEST @Value(BB_loc) = 9'2'BOOL_OP;OR;COMPOSITE_TEST;1;TEST @Value(BB_loc) = 10'1'BOOL_OP;OR;COMPOSITE_TEST;1;TEST @Value(BB_loc) = 11'1'BOOL_OP;OR;COMPOSITE_TEST;1;TEST @Value(BB_loc) = 12'1'FME_NUM_CONDITIONS14___
    -> LineBuilder_4
VertexCreator_7
    MEASURE_TYPE = Continuous
    MISSING_VAL_MODE = Compute
    MODE_NAME = Add Point
    XVAL = FME_CONDITIONAL:DEFAULT_VALUE''BOOL_OP;OR;COMPOSITE_TEST;1;TEST @Value(BB_loc) = 0'3'BOOL_OP;OR;COMPOSITE_TEST;1;TEST @Value(BB_loc) = 1'1'BOOL_OP;OR;COMPOSITE_TEST;1;TEST @Value(BB_loc) = 2'2'BOOL_OP;OR;COMPOSITE_TEST;1;TEST @Value(BB_loc) = 3'3'BOOL_OP;OR;COMPOSITE_TEST;1;TEST @Value(BB_loc) = 4'1'BOOL_OP;OR;COMPOSITE_TEST;1;TEST @Value(BB_loc) = 5'2'BOOL_OP;OR;COMPOSITE_TEST;1;TEST @Value(BB_loc) = 6'3'BOOL_OP;OR;COMPOSITE_TEST;1;TEST @Value(BB_loc) = 7'1'BOOL_OP;OR;COMPOSITE_TEST;1;TEST @Value(BB_loc) = 8'2'BOOL_OP;OR;COMPOSITE_TEST;1;TEST @Value(BB_loc) = 9'3'BOOL_OP;OR;COMPOSITE_TEST;1;TEST @Value(BB_loc) = 10'1'BOOL_OP;OR;COMPOSITE_TEST;1;TEST @Value(BB_loc) = 11'2'BOOL_OP;OR;COMPOSITE_TEST;1;TEST @Value(BB_loc) = 12'3'FME_NUM_CONDITIONS14___
    YVAL = FME_CONDITIONAL:DEFAULT_VALUE''BOOL_OP;OR;COMPOSITE_TEST;1;TEST @Value(BB_loc) = 0'4'BOOL_OP;OR;COMPOSITE_TEST;1;TEST @Value(BB_loc) = 1'4'BOOL_OP;OR;COMPOSITE_TEST;1;TEST @Value(BB_loc) = 2'4'BOOL_OP;OR;COMPOSITE_TEST;1;TEST @Value(BB_loc) = 3'4'BOOL_OP;OR;COMPOSITE_TEST;1;TEST @Value(BB_loc) = 4'3'BOOL_OP;OR;COMPOSITE_TEST;1;TEST @Value(BB_loc) = 5'3'BOOL_OP;OR;COMPOSITE_TEST;1;TEST @Value(BB_loc) = 6'3'BOOL_OP;OR;COMPOSITE_TEST;1;TEST @Value(BB_loc) = 7'2'BOOL_OP;OR;COMPOSITE_TEST;1;TEST @Value(BB_loc) = 8'2'BOOL_OP;OR;COMPOSITE_TEST;1;TEST @Value(BB_loc) = 9'2'BOOL_OP;OR;COMPOSITE_TEST;1;TEST @Value(BB_loc) = 10'1'BOOL_OP;OR;COMPOSITE_TEST;1;TEST @Value(BB_loc) = 11'1'BOOL_OP;OR;COMPOSITE_TEST;1;TEST @Value(BB_loc) = 12'1'FME_NUM_CONDITIONS14___
    -> LineBuilder_4
VertexCreator_8
    MEASURE_TYPE = Continuous
    MISSING_VAL_MODE = Compute
    MODE_NAME = Add Point
    XVAL = FME_CONDITIONAL:DEFAULT_VALUE''BOOL_OP;OR;COMPOSITE_TEST;1;TEST @Value(BB_loc) = 0'3'BOOL_OP;OR;COMPOSITE_TEST;1;TEST @Value(BB_loc) = 1'1'BOOL_OP;OR;COMPOSITE_TEST;1;TEST @Value(BB_loc) = 2'2'BOOL_OP;OR;COMPOSITE_TEST;1;TEST @Value(BB_loc) = 3'3'BOOL_OP;OR;COMPOSITE_TEST;1;TEST @Value(BB_loc) = 4'1'BOOL_OP;OR;COMPOSITE_TEST;1;TEST @Value(BB_loc) = 5'2'BOOL_OP;OR;COMPOSITE_TEST;1;TEST @Value(BB_loc) = 6'3'BOOL_OP;OR;COMPOSITE_TEST;1;TEST @Value(BB_loc) = 7'1'BOOL_OP;OR;COMPOSITE_TEST;1;TEST @Value(BB_loc) = 8'2'BOOL_OP;OR;COMPOSITE_TEST;1;TEST @Value(BB_loc) = 9'3'BOOL_OP;OR;COMPOSITE_TEST;1;TEST @Value(BB_loc) = 10'1'BOOL_OP;OR;COMPOSITE_TEST;1;TEST @Value(BB_loc) = 11'2'BOOL_OP;OR;COMPOSITE_TEST;1;TEST @Value(BB_loc) = 12'3'FME_NUM_CONDITIONS14___
    YVAL = FME_CONDITIONAL:DEFAULT_VALUE''BOOL_OP;OR;COMPOSITE_TEST;1;TEST @Value(BB_loc) = 0'0'BOOL_OP;OR;COMPOSITE_TEST;1;TEST @Value(BB_loc) = 1'3'BOOL_OP;OR;COMPOSITE_TEST;1;TEST @Value(BB_loc) = 2'3'BOOL_OP;OR;COMPOSITE_TEST;1;TEST @Value(BB_loc) = 3'3'BOOL_OP;OR;COMPOSITE_TEST;1;TEST @Value(BB_loc) = 4'2'BOOL_OP;OR;COMPOSITE_TEST;1;TEST @Value(BB_loc) = 5'2'BOOL_OP;OR;COMPOSITE_TEST;1;TEST @Value(BB_loc) = 6'2'BOOL_OP;OR;COMPOSITE_TEST;1;TEST @Value(BB_loc) = 7'1'BOOL_OP;OR;COMPOSITE_TEST;1;TEST @Value(BB_loc) = 8'1'BOOL_OP;OR;COMPOSITE_TEST;1;TEST @Value(BB_loc) = 9'1'BOOL_OP;OR;COMPOSITE_TEST;1;TEST @Value(BB_loc) = 10'0'BOOL_OP;OR;COMPOSITE_TEST;1;TEST @Value(BB_loc) = 11'0'BOOL_OP;OR;COMPOSITE_TEST;1;TEST @Value(BB_loc) = 12'0'FME_NUM_CONDITIONS14___
    -> LineBuilder_4
VertexCreator_11
    MEASURE_TYPE = Continuous
    MISSING_VAL_MODE = Compute
    MODE_NAME = Add Point
    XVAL = FME_CONDITIONAL:DEFAULT_VALUE''BOOL_OP;OR;COMPOSITE_TEST;1;TEST @Value(BB_loc) = 0'0'BOOL_OP;OR;COMPOSITE_TEST;1;TEST @Value(BB_loc) = 1'0'BOOL_OP;OR;COMPOSITE_TEST;1;TEST @Value(BB_loc) = 2'1'BOOL_OP;OR;COMPOSITE_TEST;1;TEST @Value(BB_loc) = 3'2'BOOL_OP;OR;COMPOSITE_TEST;1;TEST @Value(BB_loc) = 4'0'BOOL_OP;OR;COMPOSITE_TEST;1;TEST @Value(BB_loc) = 5'1'BOOL_OP;OR;COMPOSITE_TEST;1;TEST @Value(BB_loc) = 6'2'BOOL_OP;OR;COMPOSITE_TEST;1;TEST @Value(BB_loc) = 7'0'BOOL_OP;OR;COMPOSITE_TEST;1;TEST @Value(BB_loc) = 8'1'BOOL_OP;OR;COMPOSITE_TEST;1;TEST @Value(BB_loc) = 9'2'BOOL_OP;OR;COMPOSITE_TEST;1;TEST @Value(BB_loc) = 10'0'BOOL_OP;OR;COMPOSITE_TEST;1;TEST @Value(BB_loc) = 11'1'BOOL_OP;OR;COMPOSITE_TEST;1;TEST @Value(BB_loc) = 12'2'FME_NUM_CONDITIONS14___
    YVAL = FME_CONDITIONAL:DEFAULT_VALUE''BOOL_OP;OR;COMPOSITE_TEST;1;TEST @Value(BB_loc) = 0'0'BOOL_OP;OR;COMPOSITE_TEST;1;TEST @Value(BB_loc) = 1'3'BOOL_OP;OR;COMPOSITE_TEST;1;TEST @Value(BB_loc) = 2'3'BOOL_OP;OR;COMPOSITE_TEST;1;TEST @Value(BB_loc) = 3'3'BOOL_OP;OR;COMPOSITE_TEST;1;TEST @Value(BB_loc) = 4'2'BOOL_OP;OR;COMPOSITE_TEST;1;TEST @Value(BB_loc) = 5'2'BOOL_OP;OR;COMPOSITE_TEST;1;TEST @Value(BB_loc) = 6'2'BOOL_OP;OR;COMPOSITE_TEST;1;TEST @Value(BB_loc) = 7'1'BOOL_OP;OR;COMPOSITE_TEST;1;TEST @Value(BB_loc) = 8'1'BOOL_OP;OR;COMPOSITE_TEST;1;TEST @Value(BB_loc) = 9'1'BOOL_OP;OR;COMPOSITE_TEST;1;TEST @Value(BB_loc) = 10'0'BOOL_OP;OR;COMPOSITE_TEST;1;TEST @Value(BB_loc) = 11'0'BOOL_OP;OR;COMPOSITE_TEST;1;TEST @Value(BB_loc) = 12'0'FME_NUM_CONDITIONS14___
    -> LineBuilder_4
VertexCreator_9
    MEASURE_TYPE = Continuous
    MISSING_VAL_MODE = Compute
    MODE_NAME = Add Point
    XVAL = FME_CONDITIONAL:DEFAULT_VALUE''BOOL_OP;OR;COMPOSITE_TEST;1;TEST @Value(BB_loc) = 0'0'BOOL_OP;OR;COMPOSITE_TEST;1;TEST @Value(BB_loc) = 1'0'BOOL_OP;OR;COMPOSITE_TEST;1;TEST @Value(BB_loc) = 2'1'BOOL_OP;OR;COMPOSITE_TEST;1;TEST @Value(BB_loc) = 3'2'BOOL_OP;OR;COMPOSITE_TEST;1;TEST @Value(BB_loc) = 4'0'BOOL_OP;OR;COMPOSITE_TEST;1;TEST @Value(BB_loc) = 5'1'BOOL_OP;OR;COMPOSITE_TEST;1;TEST @Value(BB_loc) = 6'2'BOOL_OP;OR;COMPOSITE_TEST;1;TEST @Value(BB_loc) = 7'0'BOOL_OP;OR;COMPOSITE_TEST;1;TEST @Value(BB_loc) = 8'1'BOOL_OP;OR;COMPOSITE_TEST;1;TEST @Value(BB_loc) = 9'2'BOOL_OP;OR;COMPOSITE_TEST;1;TEST @Value(BB_loc) = 10'0'BOOL_OP;OR;COMPOSITE_TEST;1;TEST @Value(BB_loc) = 11'1'BOOL_OP;OR;COMPOSITE_TEST;1;TEST @Value(BB_loc) = 12'2'FME_NUM_CONDITIONS14___
    YVAL = FME_CONDITIONAL:DEFAULT_VALUE''BOOL_OP;OR;COMPOSITE_TEST;1;TEST @Value(BB_loc) = 0'4'BOOL_OP;OR;COMPOSITE_TEST;1;TEST @Value(BB_loc) = 1'4'BOOL_OP;OR;COMPOSITE_TEST;1;TEST @Value(BB_loc) = 2'4'BOOL_OP;OR;COMPOSITE_TEST;1;TEST @Value(BB_loc) = 3'4'BOOL_OP;OR;COMPOSITE_TEST;1;TEST @Value(BB_loc) = 4'3'BOOL_OP;OR;COMPOSITE_TEST;1;TEST @Value(BB_loc) = 5'3'BOOL_OP;OR;COMPOSITE_TEST;1;TEST @Value(BB_loc) = 6'3'BOOL_OP;OR;COMPOSITE_TEST;1;TEST @Value(BB_loc) = 7'2'BOOL_OP;OR;COMPOSITE_TEST;1;TEST @Value(BB_loc) = 8'2'BOOL_OP;OR;COMPOSITE_TEST;1;TEST @Value(BB_loc) = 9'2'BOOL_OP;OR;COMPOSITE_TEST;1;TEST @Value(BB_loc) = 10'1'BOOL_OP;OR;COMPOSITE_TEST;1;TEST @Value(BB_loc) = 11'1'BOOL_OP;OR;COMPOSITE_TEST;1;TEST @Value(BB_loc) = 12'1'FME_NUM_CONDITIONS14___
    -> LineBuilder_4
LineBuilder_4
    ACCUM_INPUT_ATTRS = Use Attributes From One Feature
    GROUP_BY = BB_loc
    REMOVE_DUPLICATES = No
    POLYGON -> PDFStyler_15
North_2: Creator
    GEOM = <?xml version="1.0" encoding="US_ASCII" standalone="no" ?><geometry><text><point><coord x="0" y="0"/></point><textString>null</textString><textSize>10</textSize><textRotation>0</textRotation></text></geometry>
    GEOMTYPE = Geometry Object
    NUM = 1
    CREATED -> AttributeManager_23
AttributeManager_23
    ATTR_TABLE:
      SET_TO BB_loc = $(Tile_num)
      SET_TO fme_text_string = FME_CONDITIONAL:DEFAULT_VALUE'_FME_NO_OP_'BOOL_OP;OR;COMPOSITE_TEST;1;TEST @Value(BB_loc) = 0'Full BoundingBox'BOOL_OP;OR;COMPOSITE_TEST;1;TEST @Value(BB_loc) = 1'Sub-tile n° (0,3)'BOOL_OP;OR;COMPOSITE_TEST;1;TEST @Value(BB_loc) = 2'Sub-tile n° (1,3)'BOOL_OP;OR;COMPOSITE_TEST;1;TEST @Value(BB_loc) = 3'Sub-tile n° (2,3)'BOOL_OP;OR;COMPOSITE_TEST;1;TEST @Value(BB_loc) = 4'Sub-tile n° (0,2)'BOOL_OP;OR;COMPOSITE_TEST;1;TEST @Value(BB_loc) = 5'Sub-tile n° (1,2)'BOOL_OP;OR;COMPOSITE_TEST;1;TEST @Value(BB_loc) = 6'Sub-tile n° (2,2)'BOOL_OP;OR;COMPOSITE_TEST;1;TEST @Value(BB_loc) = 7'Sub-tile n° (0,1)'BOOL_OP;OR;COMPOSITE_TEST;1;TEST @Value(BB_loc) = 8'Sub-tile n° (1,1)'BOOL_OP;OR;COMPOSITE_TEST;1;TEST @Value(BB_loc) = 9'Sub-tile n° (2,1)'BOOL_OP;OR;COMPOSITE_TEST;1;TEST @Value(BB_loc) = 10'Sub-tile n° (0,0)'BOOL_OP;OR;COMPOSITE_TEST;1;TEST @Value(BB_loc) = 11'Sub-tile n° (1,0)'BOOL_OP;OR;COMPOSITE_TEST;1;TEST @Value(BB_loc) = 12'Sub-tile n° (2,0)'FME_NUM_CONDITIONS14___
    -> PDFStyler_16
PDFStyler_16
    COLOR = 0,0.333333,1
    FILL_COLOR = 0,0.333333,1
    FILL_OPACITY = 1.00
    FONT = MS Shell Dlg 2,12,BOLD
    LINE_CAP_STYLE_PARAM = Butt Cap
    LINE_DASH_PHASE = 0
    LINE_JOIN_STYLE_PARAM = Miter Join
    LINE_MITER_LIMIT = 0.0
    LINE_WIDTH = 1.5
    OPACITY = 1.0
    PDFStyled -> PDFPageFormatter [coord]
Creator
    GEOM = <?xml version="1.0" encoding="US_ASCII" standalone="no" ?><geometry><line><coord x="0" y="4"/><coord x="3" y="4"/><coord x="3" y="0"/><coord x="0" y="0"/><coord x="0" y="4"/><coord x="1" y="4"/><coord x="1" y="0"/><coord x="2" y="0"/><coord x="2" y="4"/><coord x="3" y="4"/><coord x="3" y="3"/><coord x="0" y="3"/><coord x="0" y="2"/><coord x="3" y="2"/><coord x="3" y="1"/><coord x="0" y="1"/></line></geometry>
    GEOMTYPE = Geometry Object
    NUM = 1
    CREATED -> PDFStyler_15
PDFStyler_15
    COLOR = 0,0,0
    FILL_COLOR = 0,0.333333,1
    FILL_OPACITY = 0.51
    FONT = MS Shell Dlg 2,12,BOLD
    LINE_CAP_STYLE_PARAM = Butt Cap
    LINE_DASH_PHASE = 0
    LINE_JOIN_STYLE_PARAM = Miter Join
    LINE_MITER_LIMIT = 0.0
    LINE_WIDTH = 1.5
    OPACITY = 1.0
    PDFStyled -> PDFPageFormatter [tabular]

Bookmark: Scale
Scale_0_km_: Creator
    GEOM = <?xml version="1.0" encoding="US_ASCII" standalone="no" ?><geometry><text><point><coord x="0" y="0"/></point><textString>null</textString><textSize>10</textSize><textRotation>0</textRotation></text></geometry>
    GEOMTYPE = Geometry Object
    NUM = 1
    CREATED -> AttributeManager_15
AttributeManager_15
    ATTR_TABLE = SET_TO fme_text_string = 0
    -> PDFStyler_13
PDFStyler_13
    COLOR = 0,0,0
    FILL_COLOR = 0,0,0
    FILL_OPACITY = 1.00
    FONT = Helvetica,12
    LINE_CAP_STYLE_PARAM = Butt Cap
    LINE_DASH_PHASE = 0
    LINE_JOIN_STYLE_PARAM = Miter Join
    LINE_MITER_LIMIT = 0.0
    LINE_WIDTH = 1.0
    OPACITY = 1.0
    PDFStyled -> PDFPageFormatter [Scale 3]
Scale_left: Creator
    GEOM = <?xml version="1.0" encoding="US_ASCII" standalone="no" ?><geometry><text><point><coord x="0" y="0"/></point><textString>null</textString><textSize>1</textSize><textRotation>0</textRotation></text></geometry>
    GEOMTYPE = Geometry Object
    NUM = 1
    CREATED -> AttributeExposer_2
AttributeExposer_2
    ATTR_LIST = fme_text_string
    -> AttributeManager_20
AttributeManager_20
    ATTR_TABLE:
      SET_TO fme_type = fme_text
      SET_TO fme_text_size = 10
      SET_TO fme_feature_type = Scale_center
      SET_TO fme_geometry = fme_point
      SET_TO fme_rotation = 0
      SET_TO fme_text_string = FME_CONDITIONAL:DEFAULT_VALUE'@Evaluate(@round($(SQUARE_SIZE_KM)/12,1))'BOOL_OP;OR;COMPOSITE_TEST;1;TEST $(Tile_num) = 0'@Evaluate(@round($(SQUARE_SIZE_KM)/4,1))'FME_NUM_CONDITIONS2___
    -> PDFStyler_11
PDFStyler_11
    COLOR = 0,0,0
    FILL_COLOR = 0,0,0
    FILL_OPACITY = 1.00
    FONT = Helvetica,12
    LINE_CAP_STYLE_PARAM = Butt Cap
    LINE_DASH_PHASE = 0
    LINE_JOIN_STYLE_PARAM = Miter Join
    LINE_MITER_LIMIT = 0.0
    LINE_WIDTH = 1.0
    OPACITY = 1.0
    PDFStyled -> PDFPageFormatter [Scale 1]
Scale_center: Creator
    GEOM = <?xml version="1.0" encoding="US_ASCII" standalone="no" ?><geometry><text><point><coord x="0" y="0"/></point><textString>null</textString><textSize>1</textSize><textRotation>0</textRotation></text></geometry>
    GEOMTYPE = Geometry Object
    NUM = 1
    CREATED -> AttributeExposer
AttributeExposer
    ATTR_LIST = fme_text_string
    -> AttributeManager_18
AttributeManager_18
    ATTR_TABLE:
      SET_TO fme_text_string = FME_CONDITIONAL:DEFAULT_VALUE'@Evaluate(@round($(SQUARE_SIZE_KM)/24,1))'BOOL_OP;OR;COMPOSITE_TEST;1;TEST $(Tile_num) = 0'@Evaluate(@round($(SQUARE_SIZE_KM)/8,1))'FME_NUM_CONDITIONS2___
      SET_TO fme_type = fme_text
      SET_TO fme_text_size = 10
      SET_TO fme_feature_type = Scale_center
      SET_TO fme_geometry = fme_point
      SET_TO fme_rotation = 0
    -> PDFStyler_12
PDFStyler_12
    COLOR = 0,0,0
    FILL_COLOR = 0,0,0
    FILL_OPACITY = 1.00
    FONT = Helvetica,12
    LINE_CAP_STYLE_PARAM = Butt Cap
    LINE_DASH_PHASE = 0
    LINE_JOIN_STYLE_PARAM = Miter Join
    LINE_MITER_LIMIT = 0.0
    LINE_WIDTH = 1.0
    OPACITY = 1.0
    PDFStyled -> PDFPageFormatter [Scale 2]
Creator_4
    GEOMTYPE = Geometry Object
    NUM = 1
    CREATED -> Cloner_6
Cloner_6
    COPIES = 5
    COPYATT = _copynum
    COPY -> VertexCreator_3
VertexCreator_3
    MEASURE_TYPE = Continuous
    MISSING_VAL_MODE = Compute
    MODE_NAME = Add Point
    XVAL = FME_CONDITIONAL:DEFAULT_VALUE''BOOL_OP;OR;COMPOSITE_TEST;1 OR 2;TEST @Value(_copynum) = 0;TEST @Value(_copynum) = 4'0'BOOL_OP;OR;COMPOSITE_TEST;1;TEST @Value(_copynum) = 1'0'BOOL_OP;OR;COMPOSITE_TEST;1;TEST @Value(_copynum) = 2'8'BOOL_OP;OR;COMPOSITE_TEST;1;TEST @Value(_copynum) = 3'8'FME_NUM_CONDITIONS5___
    YVAL = FME_CONDITIONAL:DEFAULT_VALUE''BOOL_OP;OR;COMPOSITE_TEST;1 OR 2;TEST @Value(_copynum) = 0;TEST @Value(_copynum) = 4'0'BOOL_OP;OR;COMPOSITE_TEST;1;TEST @Value(_copynum) = 1'1'BOOL_OP;OR;COMPOSITE_TEST;1;TEST @Value(_copynum) = 2'1'BOOL_OP;OR;COMPOSITE_TEST;1;TEST @Value(_copynum) = 3'0'FME_NUM_CONDITIONS5___
    -> LineBuilder_6
LineBuilder_6
    ACCUM_INPUT_ATTRS = Use Attributes From One Feature
    REMOVE_DUPLICATES = No
    POLYGON -> Cloner
Cloner
    COPIES = 2
    COPYATT = _copynum
    COPY -> TestFilter_2
TestFilter_2
    DEFAULT_VALUE = right
    TEST_LIST = "BOOL_OP,OR,COMPOSITE_TEST,""""""1"""""",TEST_CLAUSE,TEST @Value(_copynum) = 0",left
    left -> PDFStyler_9
    right -> PDFStyler_10
PDFStyler_9
    COLOR = 0,0,0
    FILL_COLOR = 1,1,1
    FILL_OPACITY = 1.00
    FONT = MS Shell Dlg 2,12,BOLD
    LINE_CAP_STYLE_PARAM = Butt Cap
    LINE_DASH_PHASE = 0
    LINE_JOIN_STYLE_PARAM = Miter Join
    LINE_MITER_LIMIT = 0.0
    LINE_WIDTH = 2
    OPACITY = 1.0
    PDFStyled -> PDFPageFormatter [left_scale]
PDFStyler_10
    COLOR = 0,0,0
    FILL_COLOR = 0,0,0
    FILL_OPACITY = 1.00
    FONT = MS Shell Dlg 2,12,BOLD
    LINE_CAP_STYLE_PARAM = Butt Cap
    LINE_DASH_PHASE = 0
    LINE_JOIN_STYLE_PARAM = Miter Join
    LINE_MITER_LIMIT = 0.0
    LINE_WIDTH = 2
    OPACITY = 1.0
    PDFStyled -> PDFPageFormatter [right_scale]
Units: Creator
    GEOM = <?xml version="1.0" encoding="US_ASCII" standalone="no" ?><geometry><text><point><coord x="0" y="0"/></point><textString>Kilometers</textString><textSize>10</textSize><textRotation>0</textRotation></text></geometry>
    GEOMTYPE = Geometry Object
    NUM = 1
    CREATED -> PDFStyler_7
PDFStyler_7
    COLOR = 0,0,0
    FILL_COLOR = 0,0,0
    FILL_OPACITY = 1.00
    FONT = Helvetica,12
    LINE_CAP_STYLE_PARAM = Butt Cap
    LINE_DASH_PHASE = 0
    LINE_JOIN_STYLE_PARAM = Miter Join
    LINE_MITER_LIMIT = 0.0
    LINE_WIDTH = 1.0
    OPACITY = 1.0
    PDFStyled -> PDFPageFormatter [Units]

Bookmark: OSM layer
Creator_5
    GEOMTYPE = Geometry Object
    NUM = $(Number_of_features)
    CREATED -> AttributeManager
AttributeManager
    ATTR_TABLE:
      SET_TO attribute2print = @GetWord($(Features_to_print),@Value(_creation_instance))
      SET_TO test = $(Layer_feature)_$(ISO)\01_OSM_shp\@Value(attribute2print)\$(DATE)_$(ISO)_@Value(attribute2print)_line.shp
    -> FeatureReader_4 [INITIATOR]
    -> FeatureReader_5 [INITIATOR]
    -> FeatureReader_6 [INITIATOR]
FeatureReader_4
    ATTR_ACCUM_MODE = Merge Initiator and Result
    ATTR_CONFLICT_RES = Use Result
    ATTR_IGNORE_NULLS = No
    COMBINE_GEOM = Use Result
    DATASET = $(Layer_feature)_$(ISO)\01_OSM\@Value(attribute2print)\$(DATE)_$(ISO)_@Value(attribute2print)_line.shp
    FORMAT = SHAPEFILE
    INTERACT = <No Spatial Filter>
    OUTPUT_FEATURES_DISPLAY = Schema and Data Features
    SHAPEFILE_DONUT_DETECTION = ORIENTATION
    SHAPEFILE_ENCODING = fme-source-encoding
    SHAPEFILE_MEASURES_AS_Z = No
    SHAPEFILE_NUMERIC_TYPE_ATTRIBUTE_HANDLING = STANDARD_TYPES
    SHAPEFILE_READ_BLANK_AS = MISSING
    SHAPEFILE_REPORT_BAD_GEOMETRY = No
    SHAPEFILE_TRIM_PRECEDING_SPACES = Yes
    SHAPEFILE_USE_SEARCH_ENVELOPE = NO
    <OTHER> -> Clipper_4 [CLIPPEE]
    <REJECTED> -> Logger
FeatureReader_5
    ATTR_ACCUM_MODE = Merge Initiator and Result
    ATTR_CONFLICT_RES = Use Result
    ATTR_IGNORE_NULLS = No
    COMBINE_GEOM = Use Result
    DATASET = $(Layer_feature)_$(ISO)\01_OSM\@Value(attribute2print)\$(DATE)_$(ISO)_@Value(attribute2print)_point.shp
    FORMAT = SHAPEFILE
    INTERACT = <No Spatial Filter>
    OUTPUT_FEATURES_DISPLAY = Schema and Data Features
    SHAPEFILE_DONUT_DETECTION = ORIENTATION
    SHAPEFILE_ENCODING = fme-source-encoding
    SHAPEFILE_MEASURES_AS_Z = No
    SHAPEFILE_NUMERIC_TYPE_ATTRIBUTE_HANDLING = STANDARD_TYPES
    SHAPEFILE_READ_BLANK_AS = MISSING
    SHAPEFILE_REPORT_BAD_GEOMETRY = No
    SHAPEFILE_TRIM_PRECEDING_SPACES = Yes
    SHAPEFILE_USE_SEARCH_ENVELOPE = NO
    <OTHER> -> Clipper_4 [CLIPPEE]
    <REJECTED> -> Logger
FeatureReader_6
    ATTR_ACCUM_MODE = Merge Initiator and Result
    ATTR_CONFLICT_RES = Use Result
    ATTR_IGNORE_NULLS = No
    COMBINE_GEOM = Use Result
    DATASET = $(Layer_feature)_$(ISO)\01_OSM\@Value(attribute2print)\$(DATE)_$(ISO)_@Value(attribute2print)_polygone.shp
    FORMAT = SHAPEFILE
    INTERACT = <No Spatial Filter>
    OUTPUT_FEATURES_DISPLAY = Schema and Data Features
    SHAPEFILE_DONUT_DETECTION = ORIENTATION
    SHAPEFILE_ENCODING = fme-source-encoding
    SHAPEFILE_MEASURES_AS_Z = No
    SHAPEFILE_NUMERIC_TYPE_ATTRIBUTE_HANDLING = STANDARD_TYPES
    SHAPEFILE_READ_BLANK_AS = MISSING
    SHAPEFILE_REPORT_BAD_GEOMETRY = No
    SHAPEFILE_TRIM_PRECEDING_SPACES = Yes
    SHAPEFILE_USE_SEARCH_ENVELOPE = NO
    <OTHER> -> Clipper_4 [CLIPPEE]
    <REJECTED> -> Logger
Clipper_4
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    INSIDE -> AttributeCreator_6
    <REJECTED> -> Logger
AttributeCreator_6
    ATTR_TABLE:
      SET_TO _order = 3
      SET_TO pdf_point_width = 1.5
      SET_TO color = FME_CONDITIONAL:DEFAULT_VALUE'0,0,0'BOOL_OP;OR;COMPOSITE_TEST;1;TEST @Value(attribute2print) = highway'1,0.33,0'BOOL_OP;OR;COMPOSITE_TEST;1;TEST @Value(attribute2print) = boundary'0,0,0'BOOL_OP;OR;COMPOSITE_TEST;1;TEST @Value(attribute2print) = building'1,0,0'BOOL_OP;OR;COMPOSITE_TEST;1;TEST @Value(attribute2print) = shop'0.262,0.2039,0.4862'BOOL_OP;OR;COMPOSITE_TEST;1;TEST @Value(attribute2print) = aerialway'1,0.2,0.2'BOOL_OP;OR;COMPOSITE_TEST;1;TEST @Value(attribute2print) = aeroway'0.251,0.251,0.251'BOOL_OP;OR;COMPOSITE_TEST;1;TEST @Value(attribute2print) = amenity'0.6,0.298,0'BOOL_OP;OR;COMPOSITE_TEST;1;TEST @Value(attribute2print) = barrier'0.2,0.098,0'BOOL_OP;OR;COMPOSITE_TEST;1;TEST @Value(attribute2print) = craft'0.6901,0.7411,0.0117'BOOL_OP;OR;COMPOSITE_TEST;1;TEST @Value(attribute2print) = emergency'0.9765,0.4392,0.34901'BOOL_OP;OR;COMPOSITE_TEST;1;TEST @Value(attribute2print) = geological'0.235,0.623,0.584'BOOL_OP;OR;COMPOSITE_TEST;1;TEST @Value(attribute2print) = landuse'0.2353,0.2,0'BOOL_OP;OR;COMPOSITE_TEST;1;TEST @Value(attribute2print) = historic'0.4353,0.5686,0.4431'BOOL_OP;OR;COMPOSITE_TEST;1;TEST @Value(attribute2print) = leisure'0.08235,0.2784,0.9137'BOOL_OP;OR;COMPOSITE_TEST;1;TEST @Value(attribute2print) = man_made'0.1568,0.8471,0.4353'BOOL_OP;OR;COMPOSITE_TEST;1;TEST @Value(attribute2print) = military'0.1804,0.2,0.03921'BOOL_OP;OR;COMPOSITE_TEST;1;TEST @Value(attribute2print) = natural'0,1,0'BOOL_OP;OR;COMPOSITE_TEST;1;TEST @Value(attribute2print) = office'0.4,0,0.2'BOOL_OP;OR;COMPOSITE_TEST;1;TEST @Value(attribute2print) = place'0,0,0'BOOL_OP;OR;COMPOSITE_TEST;1;TEST @Value(attribute2print) = power'0.5,0.5,0.5'BOOL_OP;OR;COMPOSITE_TEST;1;TEST @Value(attribute2print) = public_transport'0.2,0,0.098'BOOL_OP;OR;COMPOSITE_TEST;1;TEST @Value(attribute2print) = railway'1,0,0.902'BOOL_OP;OR;COMPOSITE_TEST;1;TEST @Value(attribute2print) = route'1,1,0'BOOL_OP;OR;COMPOSITE_TEST;1;TEST @Value(attribute2print) = shop'0.2627,0.239,0.486'BOOL_OP;OR;COMPOSITE_TEST;1;TEST @Value(attribute2print) = sport'0.5843,0.5,0.4196'BOOL_OP;OR;COMPOSITE_TEST;1;TEST @Value(attribute2print) = tourism'1,0.8,0.8'BOOL_OP;OR;COMPOSITE_TEST;1;TEST @Value(attribute2print) = waterway'0,0,1'FME_NUM_CONDITIONS28___
      SET_TO line_style = FME_CONDITIONAL:DEFAULT_VALUE''BOOL_OP;OR;COMPOSITE_TEST;1;TEST @Value(attribute2print) = highway''BOOL_OP;OR;COMPOSITE_TEST;1;TEST @Value(attribute2print) = boundary'2 3 2 3'BOOL_OP;OR;COMPOSITE_TEST;1;TEST @Value(attribute2print) = building''BOOL_OP;OR;COMPOSITE_TEST;1;TEST @Value(attribute2print) = shop''BOOL_OP;OR;COMPOSITE_TEST;1;TEST @Value(attribute2print) = aerialway''BOOL_OP;OR;COMPOSITE_TEST;1;TEST @Value(attribute2print) = aeroway''BOOL_OP;OR;COMPOSITE_TEST;1;TEST @Value(attribute2print) = amenity''BOOL_OP;OR;COMPOSITE_TEST;1;TEST @Value(attribute2print) = barrier''BOOL_OP;OR;COMPOSITE_TEST;1;TEST @Value(attribute2print) = craft''BOOL_OP;OR;COMPOSITE_TEST;1;TEST @Value(attribute2print) = emergency''BOOL_OP;OR;COMPOSITE_TEST;1;TEST @Value(attribute2print) = geological''BOOL_OP;OR;COMPOSITE_TEST;1;TEST @Value(attribute2print) = landuse''BOOL_OP;OR;COMPOSITE_TEST;1;TEST @Value(attribute2print) = historic''BOOL_OP;OR;COMPOSITE_TEST;1;TEST @Value(attribute2print) = leisure''BOOL_OP;OR;COMPOSITE_TEST;1;TEST @Value(attribute2print) = man_made''BOOL_OP;OR;COMPOSITE_TEST;1;TEST @Value(attribute2print) = military''BOOL_OP;OR;COMPOSITE_TEST;1;TEST @Value(attribute2print) = natural''BOOL_OP;OR;COMPOSITE_TEST;1;TEST @Value(attribute2print) = office''BOOL_OP;OR;COMPOSITE_TEST;1;TEST @Value(attribute2print) = place''BOOL_OP;OR;COMPOSITE_TEST;1;TEST @Value(attribute2print) = power'2 3 2 3'BOOL_OP;OR;COMPOSITE_TEST;1;TEST @Value(attribute2print) = public_transport''BOOL_OP;OR;COMPOSITE_TEST;1;TEST @Value(attribute2print) = railway'2 3 2 3'BOOL_OP;OR;COMPOSITE_TEST;1;TEST @Value(attribute2print) = route''BOOL_OP;OR;COMPOSITE_TEST;1;TEST @Value(attribute2print) = shop''BOOL_OP;OR;COMPOSITE_TEST;1;TEST @Value(attribute2print) = sport''BOOL_OP;OR;COMPOSITE_TEST;1;TEST @Value(attribute2print) = tourism''BOOL_OP;OR;COMPOSITE_TEST;1;TEST @Value(attribute2print) = waterway''FME_NUM_CONDITIONS28___
      SET_TO line_phase = FME_CONDITIONAL:DEFAULT_VALUE'0'BOOL_OP;OR;COMPOSITE_TEST;1;TEST @Value(attribute2print) = highway'0'BOOL_OP;OR;COMPOSITE_TEST;1;TEST @Value(attribute2print) = boundary'10'BOOL_OP;OR;COMPOSITE_TEST;1;TEST @Value(attribute2print) = building'0'BOOL_OP;OR;COMPOSITE_TEST;1;TEST @Value(attribute2print) = shop'0'BOOL_OP;OR;COMPOSITE_TEST;1;TEST @Value(attribute2print) = aerialway'0'BOOL_OP;OR;COMPOSITE_TEST;1;TEST @Value(attribute2print) = aeroway'0'BOOL_OP;OR;COMPOSITE_TEST;1;TEST @Value(attribute2print) = amenity'0'BOOL_OP;OR;COMPOSITE_TEST;1;TEST @Value(attribute2print) = barrier'0'BOOL_OP;OR;COMPOSITE_TEST;1;TEST @Value(attribute2print) = craft'0'BOOL_OP;OR;COMPOSITE_TEST;1;TEST @Value(attribute2print) = emergency'0'BOOL_OP;OR;COMPOSITE_TEST;1;TEST @Value(attribute2print) = geological'0'BOOL_OP;OR;COMPOSITE_TEST;1;TEST @Value(attribute2print) = landuse'0'BOOL_OP;OR;COMPOSITE_TEST;1;TEST @Value(attribute2print) = historic'0'BOOL_OP;OR;COMPOSITE_TEST;1;TEST @Value(attribute2print) = leisure'0'BOOL_OP;OR;COMPOSITE_TEST;1;TEST @Value(attribute2print) = man_made'0'BOOL_OP;OR;COMPOSITE_TEST;1;TEST @Value(attribute2print) = military'0'BOOL_OP;OR;COMPOSITE_TEST;1;TEST @Value(attribute2print) = natural'0'BOOL_OP;OR;COMPOSITE_TEST;1;TEST @Value(attribute2print) = office'0'BOOL_OP;OR;COMPOSITE_TEST;1;TEST @Value(attribute2print) = place'0'BOOL_OP;OR;COMPOSITE_TEST;1;TEST @Value(attribute2print) = power'10'BOOL_OP;OR;COMPOSITE_TEST;1;TEST @Value(attribute2print) = public_transport'0'BOOL_OP;OR;COMPOSITE_TEST;1;TEST @Value(attribute2print) = railway'10'BOOL_OP;OR;COMPOSITE_TEST;1;TEST @Value(attribute2print) = route'0'BOOL_OP;OR;COMPOSITE_TEST;1;TEST @Value(attribute2print) = shop'0'BOOL_OP;OR;COMPOSITE_TEST;1;TEST @Value(attribute2print) = sport'0'BOOL_OP;OR;COMPOSITE_TEST;1;TEST @Value(attribute2print) = tourism'0'BOOL_OP;OR;COMPOSITE_TEST;1;TEST @Value(attribute2print) = waterway'0'FME_NUM_CONDITIONS28___
      SET_TO line_width = FME_CONDITIONAL:DEFAULT_VALUE'1'BOOL_OP;OR;COMPOSITE_TEST;1;TEST @Value(attribute2print) = highway'2'BOOL_OP;OR;COMPOSITE_TEST;1;TEST @Value(attribute2print) = boundary'4'BOOL_OP;OR;COMPOSITE_TEST;1;TEST @Value(attribute2print) = building'1'BOOL_OP;OR;COMPOSITE_TEST;1;TEST @Value(attribute2print) = shop'2'BOOL_OP;OR;COMPOSITE_TEST;1;TEST @Value(attribute2print) = aerialway'2'BOOL_OP;OR;COMPOSITE_TEST;1;TEST @Value(attribute2print) = aeroway'2'BOOL_OP;OR;COMPOSITE_TEST;1;TEST @Value(attribute2print) = amenity'2'BOOL_OP;OR;COMPOSITE_TEST;1;TEST @Value(attribute2print) = barrier'2'BOOL_OP;OR;COMPOSITE_TEST;1;TEST @Value(attribute2print) = craft'2'BOOL_OP;OR;COMPOSITE_TEST;1;TEST @Value(attribute2print) = emergency'2'BOOL_OP;OR;COMPOSITE_TEST;1;TEST @Value(attribute2print) = geological'1'BOOL_OP;OR;COMPOSITE_TEST;1;TEST @Value(attribute2print) = landuse'1'BOOL_OP;OR;COMPOSITE_TEST;1;TEST @Value(attribute2print) = historic'2'BOOL_OP;OR;COMPOSITE_TEST;1;TEST @Value(attribute2print) = leisure'2'BOOL_OP;OR;COMPOSITE_TEST;1;TEST @Value(attribute2print) = man_made'2'BOOL_OP;OR;COMPOSITE_TEST;1;TEST @Value(attribute2print) = military'2'BOOL_OP;OR;COMPOSITE_TEST;1;TEST @Value(attribute2print) = natural'1'BOOL_OP;OR;COMPOSITE_TEST;1;TEST @Value(attribute2print) = office'2'BOOL_OP;OR;COMPOSITE_TEST;1;TEST @Value(attribute2print) = place'4'BOOL_OP;OR;COMPOSITE_TEST;1;TEST @Value(attribute2print) = power'2'BOOL_OP;OR;COMPOSITE_TEST;1;TEST @Value(attribute2print) = public_transport'2'BOOL_OP;OR;COMPOSITE_TEST;1;TEST @Value(attribute2print) = railway'2'BOOL_OP;OR;COMPOSITE_TEST;1;TEST @Value(attribute2print) = route'2'BOOL_OP;OR;COMPOSITE_TEST;1;TEST @Value(attribute2print) = shop'2'BOOL_OP;OR;COMPOSITE_TEST;1;TEST @Value(attribute2print) = sport'2'BOOL_OP;OR;COMPOSITE_TEST;1;TEST @Value(attribute2print) = tourism'2'BOOL_OP;OR;COMPOSITE_TEST;1;TEST @Value(attribute2print) = waterway'3'FME_NUM_CONDITIONS28___
    -> TestFilter_3
TestFilter_3
    DEFAULT_VALUE = solid_line
    TEST_LIST = "BOOL_OP,OR,COMPOSITE_TEST,""""""1"""""",TEST_CLAUSE,TEST @Value(attribute2print) = boundary",dashed_line,"BOOL_OP,OR,COMPOSITE_TEST,""""""1"""""",TEST_CLAUSE,TEST @Value(attribute2print) = railway",dashed_line,"BOOL_OP,OR,COMPOSITE_TEST,""""""1"""""",TEST_CLAUSE,TEST @Value(attribute2print) = power",dashed_line
    dashed_line -> TestFilter
    solid_line -> PDFStyler_18
PDFStyler_18
    COLOR = @Value(color)
    FILL_COLOR = @Value(color)
    FILL_OPACITY = 0.72
    FONT = Helvetica,14,ITALIC
    LINE_CAP_STYLE_PARAM = Butt Cap
    LINE_DASH_PHASE = @Value(line_phase)
    LINE_JOIN_STYLE_PARAM = Miter Join
    LINE_MITER_LIMIT = 0.0
    LINE_WIDTH = @Value(line_width)
    OPACITY = 1.0
    PDFStyled -> Sorter
TestFilter
    DEFAULT_VALUE = normal
    TEST_LIST = "BOOL_OP,OR,COMPOSITE_TEST,""""""1"""""",TEST_CLAUSE,TEST @Value(attribute2print) = boundary",fillzero
    fillzero -> PDFStyler_20
    normal -> PDFStyler_17
PDFStyler_20
    COLOR = @Value(color)
    FILL_COLOR = 1,1,1
    FILL_OPACITY = 0.00
    FONT = Helvetica,14,ITALIC
    LINE_CAP_STYLE_PARAM = Butt Cap
    LINE_DASH_ARRAY = 2 3 2 3
    LINE_DASH_PHASE = @Value(line_phase)
    LINE_JOIN_STYLE_PARAM = Miter Join
    LINE_MITER_LIMIT = 0.0
    LINE_WIDTH = @Value(line_width)
    OPACITY = 1.0
    PDFStyled -> Sorter
PDFStyler_17
    COLOR = @Value(color)
    FILL_COLOR = @Value(color)
    FILL_OPACITY = 0.15
    FONT = Helvetica,14,ITALIC
    LINE_CAP_STYLE_PARAM = Butt Cap
    LINE_DASH_ARRAY = 2 3 2 3
    LINE_DASH_PHASE = @Value(line_phase)
    LINE_JOIN_STYLE_PARAM = Miter Join
    LINE_MITER_LIMIT = 0.0
    LINE_WIDTH = @Value(line_width)
    OPACITY = 1.0
    PDFStyled -> Sorter
Logger
    LOG_FEATURE = LOG_ONLY
    MAXCOORDS = 20
    MAXFEATS = 20
    MESSAGE = Feature is:
    SEVERITY = INFO

Bookmark: North Arrow
Creator_3
    GEOMTYPE = Geometry Object
    NUM = 1
    CREATED -> Cloner_5
Cloner_5
    COPIES = 5
    COPYATT = _copynum
    COPY -> VertexCreator_5
VertexCreator_5
    MEASURE_TYPE = Continuous
    MISSING_VAL_MODE = Compute
    MODE_NAME = Add Point
    XVAL = FME_CONDITIONAL:DEFAULT_VALUE''BOOL_OP;OR;COMPOSITE_TEST;1 OR 2;TEST @Value(_copynum) = 0;TEST @Value(_copynum) = 4'0'BOOL_OP;OR;COMPOSITE_TEST;1;TEST @Value(_copynum) = 1'1'BOOL_OP;OR;COMPOSITE_TEST;1;TEST @Value(_copynum) = 2'2'BOOL_OP;OR;COMPOSITE_TEST;1;TEST @Value(_copynum) = 3'1'FME_NUM_CONDITIONS5___
    YVAL = FME_CONDITIONAL:DEFAULT_VALUE''BOOL_OP;OR;COMPOSITE_TEST;1 OR 2;TEST @Value(_copynum) = 0;TEST @Value(_copynum) = 4'0'BOOL_OP;OR;COMPOSITE_TEST;1;TEST @Value(_copynum) = 1'2.5'BOOL_OP;OR;COMPOSITE_TEST;1;TEST @Value(_copynum) = 2'0'BOOL_OP;OR;COMPOSITE_TEST;1;TEST @Value(_copynum) = 3'0.8'FME_NUM_CONDITIONS5___
    -> LineBuilder_5
LineBuilder_5
    ACCUM_INPUT_ATTRS = Use Attributes From One Feature
    REMOVE_DUPLICATES = No
    POLYGON -> PDFStyler_6
PDFStyler_6
    COLOR = 0,0,0
    FILL_COLOR = 0,0,0
    FILL_OPACITY = 1.00
    FONT = MS Shell Dlg 2,12,BOLD
    LINE_CAP_STYLE_PARAM = Butt Cap
    LINE_DASH_PHASE = 0
    LINE_JOIN_STYLE_PARAM = Miter Join
    LINE_MITER_LIMIT = 0.0
    LINE_WIDTH = 1.5
    OPACITY = 1.0
    PDFStyled -> PDFPageFormatter [arrow]
North: Creator
    GEOM = <?xml version="1.0" encoding="US_ASCII" standalone="no" ?><geometry><text><point><coord x="0" y="0"/></point><textString>null</textString><textSize>10</textSize><textRotation>0</textRotation></text></geometry>
    GEOMTYPE = Geometry Object
    NUM = 1
    CREATED -> AttributeManager_13
AttributeManager_13
    ATTR_TABLE = SET_TO fme_text_string = N
    -> PDFStyler_14
PDFStyler_14
    COLOR = 0,0,0
    FILL_COLOR = 0,0,0
    FILL_OPACITY = 1.00
    FONT = MS Shell Dlg 2,12,BOLD
    LINE_CAP_STYLE_PARAM = Butt Cap
    LINE_DASH_PHASE = 0
    LINE_JOIN_STYLE_PARAM = Miter Join
    LINE_MITER_LIMIT = 0.0
    LINE_WIDTH = 1.0
    OPACITY = 1.0
    PDFStyled -> PDFPageFormatter [North]

Bookmark: TItle & Signature
Title: Creator
    GEOM = <?xml version="1.0" encoding="US_ASCII" standalone="no" ?><geometry><text><point><coord x="0" y="0"/></point><textString>Cartographic output</textString><textSize>1</textSize><textRotation>0</textRotation></text></geometry>
    GEOMTYPE = Geometry Object
    NUM = 1
    CREATED -> PDFStyler
PDFStyler
    COLOR = 0,0,0
    FILL_COLOR = 0,0,0
    FILL_OPACITY = 0.60
    FONT = Helvetica,16
    LINE_CAP_STYLE_PARAM = Butt Cap
    LINE_DASH_PHASE = 0
    LINE_JOIN_STYLE_PARAM = Miter Join
    LINE_MITER_LIMIT = 0.0
    LINE_WIDTH = 1.0
    OPACITY = 1.0
    PDFStyled -> PDFPageFormatter [Title_Frame]
    PDFStyled -> PDFPageFormatter_2 [header]
Signature: Creator
    GEOM = <?xml version="1.0" encoding="US_ASCII" standalone="no" ?><geometry><text><point><coord x="0" y="0"/></point><textString>HGDR project, INSER SA, 2022</textString><textSize>10</textSize><textRotation>0</textRotation></text></geometry>
    GEOMTYPE = Geometry Object
    NUM = 1
    CREATED -> PDFStyler_2
PDFStyler_2
    COLOR = 0,0,0
    FILL_COLOR = 0,0,0
    FILL_OPACITY = 0.4
    FONT = Helvetica,12,ITALIC
    LINE_CAP_STYLE_PARAM = Butt Cap
    LINE_DASH_PHASE = 0
    LINE_JOIN_STYLE_PARAM = Miter Join
    LINE_MITER_LIMIT = 0.0
    LINE_WIDTH = 1.0
    OPACITY = 1.0
    PDFStyled -> PDFPageFormatter [Signature_Frame]
    PDFStyled -> PDFPageFormatter_2 [signature]
