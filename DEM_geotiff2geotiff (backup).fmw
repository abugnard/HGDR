FME workspace DEM_geotiff2geotiff (backup).fmw

Parameters:
- SourceDataset_GEOTIFF = $(FME_MF_DIR)DEM\GMTED2010N10E030_075(1)\10n030e_20101117_gmted_dsc075.tif   # Source GeoTIFF File(s)
- DestDataset_GEOTIFF = $(FME_MF_DIR)output_DEM   # Destination GeoTIFF Folder
- SourceDataset_GEOTIFF_2 = $(FME_MF_DIR)DEM\GMTED2010N10E000_075\10n000e_20101117_gmted_dsc075.tif   # Source GeoTIFF File(s)
- SourceDataset_GEOTIFF_19 = $(FME_MF_DIR)DEM\GMTED2010N10E060_075\10n060e_20101117_gmted_dsc075.tif   # Source GeoTIFF File(s)
- SourceDataset_GEOTIFF_15 = $(FME_MF_DIR)DEM\GMTED2010N10E090_075\10n090e_20101117_gmted_dsc075.tif   # Source GeoTIFF File(s)
- SourceDataset_GEOTIFF_13 = $(FME_MF_DIR)DEM\GMTED2010N10E120_075\10n120e_20101117_gmted_dsc075.tif   # Source GeoTIFF File(s)
- SourceDataset_GEOTIFF_17 = $(FME_MF_DIR)DEM\GMTED2010N10E150_075\10n150e_20101117_gmted_dsc075.tif   # Source GeoTIFF File(s)
- SourceDataset_GEOTIFF_12 = $(FME_MF_DIR)DEM\GMTED2010N10W060_075\10n060w_20101117_gmted_dsc075.tif   # Source GeoTIFF File(s)
- SourceDataset_GEOTIFF_14 = $(FME_MF_DIR)DEM\GMTED2010N10W030_075\10n030w_20101117_gmted_dsc075.tif   # Source GeoTIFF File(s)
- SourceDataset_GEOTIFF_16 = $(FME_MF_DIR)DEM\GMTED2010N10W120_075\10n120w_20101117_gmted_dsc075.tif   # Source GeoTIFF File(s)
- SourceDataset_GEOTIFF_18 = $(FME_MF_DIR)DEM\GMTED2010N10W090_075\10n090w_20101117_gmted_dsc075.tif   # Source GeoTIFF File(s)

Readers:
- GEOTIFF_1: GEOTIFF from $(SourceDataset_GEOTIFF)
- GEOTIFF_3: GEOTIFF from $(SourceDataset_GEOTIFF_2)
- GEOTIFF_4: GEOTIFF from $(SourceDataset_GEOTIFF_19)
- GEOTIFF_5: GEOTIFF from $(SourceDataset_GEOTIFF_15)
- GEOTIFF_6: GEOTIFF from $(SourceDataset_GEOTIFF_13)
- GEOTIFF_7: GEOTIFF from $(SourceDataset_GEOTIFF_17)
- GEOTIFF_8: GEOTIFF from $(SourceDataset_GEOTIFF_12)
- GEOTIFF_9: GEOTIFF from $(SourceDataset_GEOTIFF_14)
- GEOTIFF_10: GEOTIFF from $(SourceDataset_GEOTIFF_16)
- GEOTIFF_11: GEOTIFF from $(SourceDataset_GEOTIFF_18)

Writers:
- GEOTIFF_2: GEOTIFF to $(DestDataset_GEOTIFF)

RasterMosaicker
    ACCUM_ATTRS_NAME = Use Attributes From One Feature
    INTERPOLATION_TYPE_NAME = Nearest Neighbor
    MERGE_PALETTES_NAME = Yes
    NODATA_OVERWRITE = No
    OVERLAPPING_VALUES = last
    SNAPPING_TYPE_NAME = Offset
    -> GEOTIFF (writer GEOTIFF_2)

Bookmark: 10/-120
GEOTIFF (reader GEOTIFF_10)
    -> RasterMosaicker

Bookmark: 10/-90
GEOTIFF (reader GEOTIFF_11)
    -> RasterMosaicker

Bookmark: 10/-60
GEOTIFF (reader GEOTIFF_8)
    -> RasterMosaicker

Bookmark: 10/-30
GEOTIFF (reader GEOTIFF_9)
    -> RasterMosaicker

Bookmark: 10/00
GEOTIFF (reader GEOTIFF_3)
    -> RasterMosaicker

Bookmark: 10/30
GEOTIFF (reader GEOTIFF_1)
    -> RasterMosaicker

Bookmark: 10/60
GEOTIFF (reader GEOTIFF_4)
    -> RasterMosaicker

Bookmark: 10/90
GEOTIFF (reader GEOTIFF_5)
    -> RasterMosaicker

Bookmark: 10/120
GEOTIFF (reader GEOTIFF_6)
    -> RasterMosaicker

Bookmark: 10/150
GEOTIFF (reader GEOTIFF_7)
    -> RasterMosaicker

Bookmark: Writer Feature Types
GEOTIFF (writer GEOTIFF_2)
