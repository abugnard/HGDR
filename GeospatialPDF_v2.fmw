FME workspace GeospatialPDF_v2.fmw
Title: Geospatial PDF - Cartographic Output

Parameters:
- SourceDataset_JPEG2000 = $(FME_MF_DIR)output_AM_AZ_GE\04_Basemap\subtiles\subbasemap_AM_AZ_GE_3.jp2   # Source JPEG 2000 File(s)
- Zoom = 11   # Zoom of the basemap
- Coord_LR_x = 45.136211905602366   # Coordinates lower right corner
- Coord_LR_y = 41.18974700036295   # Coordinates lower right corner
- FILE_name = BoundingBox   # Choose filename
- Layer_1 = $(FME_MF_DIR)output_AM_AZ_GE\waterway\20220616_AM_AZ_GE_waterway_line.shp   # Destination of the layer to map
- Layer_2 = $(FME_MF_DIR)output_AM_AZ_GE\highway\20220616_AM_AZ_GE_highway_line.shp   # Destination of the layer to map
- DestDataset_PDF2D = $(FME_MF_DIR)output_AM_AZ_GE\05_export_PDF\$(FILE_name)_PDF.pdf   # Destination Adobe Geospatial PDF File
- Tile_num = 4   # Part of the boundingbox
- SQUARE_SIZE_KM = 20   # Square size [km]

Readers:
- JPEG2000_1: JPEG2000 from $(SourceDataset_JPEG2000) in LL-WGS84
- PDF2D_1: PDF2D from $(FME_MF_DIR)PDF_legend.pdf
- ARCGIS_LAYER_1: ARCGIS_LAYER from C:\Users\alexandre\Downloads\World_Continents.lpk

Writers:
- PDF2D_2: PDF2D to $(DestDataset_PDF2D)

JPEG2000 (reader JPEG2000_1)
    -> BoundingBoxAccumulator
    -> AttributeCreator
AttributeCreator
    ATTR_TABLE:
      SET_TO _order = 0
      SET_TO fme_feature_type = BackgroundMap
    -> Sorter
BoundingBoxAccumulator
    ACCUM_ATTRS_NAME = Use Attributes From One Feature
    BOUNDING_BOX -> AttributeCreator_2
    BOUNDING_BOX -> Clipper [CLIPPER]
    BOUNDING_BOX -> Clipper_2 [CLIPPER]
    BOUNDING_BOX -> CoordinateExtractor
AttributeCreator_2
    ATTR_TABLE:
      SET_TO _order = 1
      SET_TO fme_feature_type = BoundingBox
    -> PDFStyler_3
PDFStyler_3
    COLOR = 0,0,0
    FILL_COLOR = 0,0,0
    FILL_OPACITY = 0
    FONT = Helvetica,9
    LINE_CAP_STYLE_PARAM = Butt Cap
    LINE_DASH_PHASE = 0
    LINE_JOIN_STYLE_PARAM = Miter Join
    LINE_MITER_LIMIT = 0.0
    LINE_WIDTH = 3
    OPACITY = 1.0
    PDFStyled -> Sorter
CoordinateExtractor
    LIST_NAME = _indices
    MODE = All Coordinates
    -> AttributeManager_4
    -> AttributeManager_7
    -> AttributeManager_10
AttributeManager_10
    ATTR_TABLE:
      SET_TO arrow1x = @Evaluate($(Coord_LR_x))
      SET_TO arrow1y = @Evaluate(@sub($(Coord_LR_y),@mult((@Value(_indices{1}.x)-@Value(_indices{0}.x))*0.06,@cos(@mult(@pi(),0.555555555,$(Coord_LR_y))))))
      SET_TO arrow2x = @Evaluate($(Coord_LR_x)-(@Value(_indices{1}.x)-@Value(_indices{0}.x))*0.3)
      SET_TO arrow2y = @Evaluate(@sub($(Coord_LR_y),@mult((@Value(_indices{1}.x)-@Value(_indices{0}.x))*0.06,@cos(@mult(@pi(),0.555555555,$(Coord_LR_y))))))
      SET_TO dist = @Evaluate(@abs(@Value(arrow1x)-@Value(arrow2x)))
    -> Cloner_4 [off]
Cloner_4 [off]
    COPIES = 3
    COPYATT = _copynum
    COPY -> AttributeManager_11
AttributeManager_11 [off]
    ATTR_TABLE:
      SET_TO label_pos_x = FME_CONDITIONAL:DEFAULT_VALUE'_FME_NO_OP_'BOOL_OP;OR;COMPOSITE_TEST;1;TEST @Value(_copynum) = 0'@Evaluate(@Value(arrow1x)-@Value(dist))'BOOL_OP;OR;COMPOSITE_TEST;1;TEST @Value(_copynum) = 1'@Evaluate(@Value(arrow1x)-(@Value(dist)/2))'BOOL_OP;OR;COMPOSITE_TEST;1;TEST @Value(_copynum) = 2'@Value(arrow1x)'FME_NUM_CONDITIONS4___
      SET_TO label_pos_y = @Value(arrow1y)
      SET_TO scale_to_print = @Evaluate(@round(@mult(@abs(@Value(arrow1x)-@Value(label_pos_x)),111),1))
    -> GeometryRemover_5
GeometryRemover_5 [off]
    -> AttributeManager_16
AttributeManager_16 [off]
    ATTR_TABLE:
      REMOVE _indices{}.x
      REMOVE _indices{}.y
      REMOVE _indices{}.z
      REMOVE arrow1x
      REMOVE arrow1y
      REMOVE arrow2x
      REMOVE arrow2y
      REMOVE label_pos_x
      REMOVE label_pos_y
      REMOVE dist
    -> TestFilter
TestFilter [off]
    DEFAULT_VALUE = <UNFILTERED>
    TEST_LIST = "BOOL_OP,OR,COMPOSITE_TEST,""""""1"""""",TEST_CLAUSE,TEST @Value(_copynum) = 0",left_scale,"BOOL_OP,OR,COMPOSITE_TEST,""""""1"""""",TEST_CLAUSE,TEST @Value(_copynum) = 1",center_scale
    left_scale -> AttributeManager_21
    center_scale -> AttributeManager_17
AttributeManager_17 [off]
    ATTR_TABLE:
      SET_TO fme_text_string = @Value(scale_to_print) [km]
      REMOVE fme_basename
      REMOVE _copynum
      REMOVE scale_to_print
      SET_TO _creation_instance = 0
    -> FeatureMerger [SUPPLIER]
AttributeManager_21 [off]
    ATTR_TABLE:
      SET_TO fme_text_string = @Value(scale_to_print) [km]
      REMOVE fme_basename
      REMOVE _copynum
      REMOVE scale_to_print
      SET_TO _creation_instance = 0
    -> FeatureMerger_2 [REQUESTOR]
LineBuilder_3
    ACCUM_INPUT_ATTRS = Use Attributes From One Feature
    GROUP_BY = fme_basename
    REMOVE_DUPLICATES = No
    POLYGON -> AttributeCreator_6
AttributeCreator_6
    ATTR_TABLE:
      SET_TO _order = 4
      SET_TO pdf_point_width = 1.5
    -> PDFStyler_7
PDFStyler_7
    COLOR = 0,0,0
    FILL_COLOR = 1,1,1
    FILL_OPACITY = 1.00
    FONT = Helvetica,14,ITALIC
    LINE_CAP_STYLE_PARAM = Butt Cap
    LINE_DASH_PHASE = 0
    LINE_JOIN_STYLE_PARAM = Round Join
    LINE_MITER_LIMIT = 2
    LINE_WIDTH = 3
    OPACITY = 1.00
    PDFStyled -> Sorter
LineBuilder_2
    ACCUM_INPUT_ATTRS = Use Attributes From One Feature
    GROUP_BY = fme_basename
    REMOVE_DUPLICATES = No
    POLYGON -> AttributeCreator_7
AttributeCreator_7
    ATTR_TABLE = SET_TO _order = 4
    -> PDFStyler_8
PDFStyler_8
    COLOR = 0,0,0
    FILL_COLOR = 0,0,0
    FILL_OPACITY = 1.00
    FONT = Helvetica,0.1,ITALIC
    LINE_CAP_STYLE_PARAM = Butt Cap
    LINE_DASH_PHASE = 0
    LINE_JOIN_STYLE_PARAM = Round Join
    LINE_MITER_LIMIT = 2
    LINE_WIDTH = 3
    OPACITY = 1.00
    PDFStyled -> Sorter
Creator_5
    GEOMTYPE = Geometry Object
    NUM = 1
    CREATED -> FeatureReader_2 [INITIATOR]
    CREATED -> FeatureReader [INITIATOR]
FeatureReader_2
    ATTR_ACCUM_MODE = Only Use Result
    COMBINE_GEOM = Use Result
    DATASET = $(Layer_1)
    FORMAT = SHAPEFILE
    INTERACT = <No Spatial Filter>
    OUTPUT_FEATURES_DISPLAY = Schema and Data Features
    SHAPEFILE_DONUT_DETECTION = ORIENTATION
    SHAPEFILE_ENCODING = fme-source-encoding
    SHAPEFILE_MEASURES_AS_Z = No
    SHAPEFILE_NUMERIC_TYPE_ATTRIBUTE_HANDLING = STANDARD_TYPES
    SHAPEFILE_READ_BLANK_AS = MISSING
    SHAPEFILE_REPORT_BAD_GEOMETRY = No
    SHAPEFILE_TRIM_PRECEDING_SPACES = Yes
    SHAPEFILE_USE_SEARCH_ENVELOPE = NO
    <OTHER> -> Clipper_2 [CLIPPEE]
Clipper_2
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    INSIDE -> AttributeCreator_4
AttributeCreator_4
    ATTR_TABLE:
      SET_TO _order = 3
      SET_TO pdf_point_width = 1.5
    -> PDFStyler_5
PDFStyler_5
    COLOR = 0,0,1
    FILL_COLOR = 0,0,1
    FILL_OPACITY = 0.4
    FONT = Helvetica,14,ITALIC
    LINE_CAP_STYLE_PARAM = Butt Cap
    LINE_DASH_PHASE = 0
    LINE_JOIN_STYLE_PARAM = Miter Join
    LINE_MITER_LIMIT = 0.0
    LINE_WIDTH = 2
    OPACITY = 1.0
    PDFStyled -> Sorter
FeatureReader
    ATTRIBUTES = 20220609_BS_highway_line,"addr:house,addr:stree,admin_leve,aerialway,aeroway,amenity,barrier,boundary,building,bus,craft,electrifie,emergency,fire_hydra,fire_hyd00,fire_hyd01,fme_geomet,fme_geom00,fme_geom01,fme_geom02,fme_geom03,gauge,geological,highway,historic,informatio,landuse,leisure,man_made,military,name,natural,network,office,place,power,public_tra,railway,ref,route,shop,source,sport,tourism,type,waterway,name:en,official_n,wikidata,according_,accordin00,accordin01,accordin02,accordin03,accordin04,accordin05"
    ATTR_ACCUM_MODE = Only Use Result
    COMBINE_GEOM = Use Result
    DATASET = $(Layer_2)
    FORMAT = SHAPEFILE
    INTERACT = <No Spatial Filter>
    OUTPUT_FEATURES_DISPLAY = Schema and Data Features
    SHAPEFILE_DONUT_DETECTION = ORIENTATION
    SHAPEFILE_ENCODING = fme-source-encoding
    SHAPEFILE_MEASURES_AS_Z = No
    SHAPEFILE_NUMERIC_TYPE_ATTRIBUTE_HANDLING = STANDARD_TYPES
    SHAPEFILE_READ_BLANK_AS = MISSING
    SHAPEFILE_REPORT_BAD_GEOMETRY = No
    SHAPEFILE_TRIM_PRECEDING_SPACES = Yes
    SHAPEFILE_USE_SEARCH_ENVELOPE = NO
    <OTHER> -> Clipper [CLIPPEE]
Clipper
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    INSIDE -> AttributeCreator_3
AttributeCreator_3
    ATTR_TABLE = SET_TO _order = 2
    -> PDFStyler_4
PDFStyler_4
    COLOR = 1,0.333333,0
    FILL_COLOR = 1,0.333333,0
    FILL_OPACITY = 1.00
    FONT = Helvetica,9
    LINE_CAP_STYLE_PARAM = Butt Cap
    LINE_DASH_PHASE = 0
    LINE_JOIN_STYLE_PARAM = Miter Join
    LINE_MITER_LIMIT = 0
    LINE_WIDTH = 1
    OPACITY = 1.0
    PDFStyled -> Sorter
Note: Sort drawing order with _order
Sorter
    SORT_PARM = _order NUMERIC ASCENDING
    SORTED -> PDFPageFormatter [Main]
Scale_0_km_: Creator
    GEOM = <?xml version="1.0" encoding="US_ASCII" standalone="no" ?><geometry><text><point><coord x="0" y="0"/></point><textString>null</textString><textSize>10</textSize><textRotation>0</textRotation></text></geometry>
    GEOMTYPE = Geometry Object
    NUM = 1
    CREATED -> AttributeManager_15
AttributeManager_15
    ATTR_TABLE = SET_TO fme_text_string = 0
    -> PDFStyler_13
PDFStyler_13
    COLOR = 0,0,0
    FILL_COLOR = 0,0,0
    FILL_OPACITY = 1.00
    FONT = Helvetica,12
    LINE_CAP_STYLE_PARAM = Butt Cap
    LINE_DASH_PHASE = 0
    LINE_JOIN_STYLE_PARAM = Miter Join
    LINE_MITER_LIMIT = 0.0
    LINE_WIDTH = 1.0
    OPACITY = 1.0
    PDFStyled -> PDFPageFormatter [Scale 3]
Scale_left: Creator
    GEOM = <?xml version="1.0" encoding="US_ASCII" standalone="no" ?><geometry><text><point><coord x="0" y="0"/></point><textString>null</textString><textSize>1</textSize><textRotation>0</textRotation></text></geometry>
    GEOMTYPE = Geometry Object
    NUM = 1
    CREATED -> AttributeManager_19
    CREATED -> AttributeManager_20
AttributeManager_19 [off]
    -> FeatureMerger_2 [SUPPLIER]
FeatureMerger_2 [off]
    ATTR_ACCUM_MODE = Merge Supplier
    ATTR_CONFLICT_RES = Use Requestor
    CLEANING_TOLERANCE = Automatic
    CONNECT_Z_MODE = First Wins
    GEOM_TYPE = Build Polygons
    GROUP_BY = _creation_instance
    IGNORE_NULLS = No
    JOIN_KEYS = @Value(_creation_instance) @Value(_creation_instance) AUTO
    MERGE_TYPE = Attributes and Geometry
    PROCESS_DUPS = YES
    REJECT_NULL_MISSING_KEYS = No
    SUPPLIERS_FIRST = Yes
    MERGED -> AttributeManager_20
AttributeManager_20
    ATTR_TABLE:
      SET_TO fme_text_string = FME_CONDITIONAL:DEFAULT_VALUE'@Evaluate($(SQUARE_SIZE_KM)/12 [km])'BOOL_OP;OR;COMPOSITE_TEST;1;TEST $(Tile_num) = 0'@Evaluate(@round($(SQUARE_SIZE_KM)/4,1) [km])'FME_NUM_CONDITIONS2___
      SET_TO fme_type = fme_text
      SET_TO fme_text_size = 10
      SET_TO fme_feature_type = Scale_center
      SET_TO fme_geometry = fme_point
      SET_TO fme_rotation = 0
    -> PDFStyler_11
PDFStyler_11
    COLOR = 0,0,0
    FILL_COLOR = 0,0,0
    FILL_OPACITY = 1.00
    FONT = Helvetica,12
    LINE_CAP_STYLE_PARAM = Butt Cap
    LINE_DASH_PHASE = 0
    LINE_JOIN_STYLE_PARAM = Miter Join
    LINE_MITER_LIMIT = 0.0
    LINE_WIDTH = 1.0
    OPACITY = 1.0
    PDFStyled -> PDFPageFormatter [Scale 1]
Title: Creator
    GEOM = <?xml version="1.0" encoding="US_ASCII" standalone="no" ?><geometry><text><point><coord x="0" y="0"/></point><textString>Cartographic output</textString><textSize>1</textSize><textRotation>0</textRotation></text></geometry>
    GEOMTYPE = Geometry Object
    NUM = 1
    CREATED -> PDFStyler
PDFStyler
    COLOR = 0,0,0
    FILL_COLOR = 0,0,0
    FILL_OPACITY = 0.60
    FONT = Helvetica,16
    LINE_CAP_STYLE_PARAM = Butt Cap
    LINE_DASH_PHASE = 0
    LINE_JOIN_STYLE_PARAM = Miter Join
    LINE_MITER_LIMIT = 0.0
    LINE_WIDTH = 1.0
    OPACITY = 1.0
    PDFStyled -> PDFPageFormatter [Title_Frame]
Signature: Creator
    GEOM = <?xml version="1.0" encoding="US_ASCII" standalone="no" ?><geometry><text><point><coord x="0" y="0"/></point><textString>HGDR project, INSER SA, 2022</textString><textSize>10</textSize><textRotation>0</textRotation></text></geometry>
    GEOMTYPE = Geometry Object
    NUM = 1
    CREATED -> PDFStyler_2
PDFStyler_2
    COLOR = 0,0,0
    FILL_COLOR = 0,0,0
    FILL_OPACITY = 0.4
    FONT = Helvetica,12,ITALIC
    LINE_CAP_STYLE_PARAM = Butt Cap
    LINE_DASH_PHASE = 0
    LINE_JOIN_STYLE_PARAM = Miter Join
    LINE_MITER_LIMIT = 0.0
    LINE_WIDTH = 1.0
    OPACITY = 1.0
    PDFStyled -> PDFPageFormatter [Signature_Frame]
Scale_center: Creator
    GEOM = <?xml version="1.0" encoding="US_ASCII" standalone="no" ?><geometry><text><point><coord x="0" y="0"/></point><textString>null</textString><textSize>1</textSize><textRotation>0</textRotation></text></geometry>
    GEOMTYPE = Geometry Object
    NUM = 1
    CREATED -> AttributeManager_14
    CREATED -> AttributeManager_18
AttributeManager_14 [off]
    -> FeatureMerger [REQUESTOR]
FeatureMerger [off]
    ATTR_ACCUM_MODE = Merge Supplier
    ATTR_CONFLICT_RES = Use Requestor
    CLEANING_TOLERANCE = Automatic
    CONNECT_Z_MODE = First Wins
    GEOM_TYPE = Build Polygons
    GROUP_BY = _creation_instance
    IGNORE_NULLS = No
    JOIN_KEYS = @Value(_creation_instance) @Value(_creation_instance) AUTO
    MERGE_TYPE = Attributes and Geometry
    PROCESS_DUPS = YES
    REJECT_NULL_MISSING_KEYS = No
    SUPPLIERS_FIRST = Yes
    MERGED -> AttributeManager_18
AttributeManager_18
    ATTR_TABLE:
      SET_TO fme_text_string = FME_CONDITIONAL:DEFAULT_VALUE'@Evaluate(@round($(SQUARE_SIZE_KM)/24,1))'BOOL_OP;OR;COMPOSITE_TEST;1;TEST $(Tile_num) = 0'@Evaluate(@round($(SQUARE_SIZE_KM)/8,1))'FME_NUM_CONDITIONS2___
      SET_TO fme_type = fme_text
      SET_TO fme_text_size = 10
      SET_TO fme_feature_type = Scale_center
      SET_TO fme_geometry = fme_point
      SET_TO fme_rotation = 0
    -> PDFStyler_12
PDFStyler_12
    COLOR = 0,0,0
    FILL_COLOR = 0,0,0
    FILL_OPACITY = 1.00
    FONT = Helvetica,12
    LINE_CAP_STYLE_PARAM = Butt Cap
    LINE_DASH_PHASE = 0
    LINE_JOIN_STYLE_PARAM = Miter Join
    LINE_MITER_LIMIT = 0.0
    LINE_WIDTH = 1.0
    OPACITY = 1.0
    PDFStyled -> PDFPageFormatter [Scale 2]
North: Creator
    GEOM = <?xml version="1.0" encoding="US_ASCII" standalone="no" ?><geometry><text><point><coord x="0" y="0"/></point><textString>null</textString><textSize>10</textSize><textRotation>0</textRotation></text></geometry>
    GEOMTYPE = Geometry Object
    NUM = 1
    CREATED -> AttributeManager_13
AttributeManager_13
    ATTR_TABLE = SET_TO fme_text_string = N
    -> PDFStyler_14
PDFStyler_14
    COLOR = 0,0,0
    FILL_COLOR = 0,0,0
    FILL_OPACITY = 1.00
    FONT = MS Shell Dlg 2,12,BOLD
    LINE_CAP_STYLE_PARAM = Butt Cap
    LINE_DASH_PHASE = 0
    LINE_JOIN_STYLE_PARAM = Miter Join
    LINE_MITER_LIMIT = 0.0
    LINE_WIDTH = 1.0
    OPACITY = 1.0
    PDFStyled -> PDFPageFormatter [North]
Creator_3
    GEOMTYPE = Geometry Object
    NUM = 1
    CREATED -> Cloner_5
Cloner_5
    COPIES = 5
    COPYATT = _copynum
    COPY -> VertexCreator_5
VertexCreator_5
    MEASURE_TYPE = Continuous
    MISSING_VAL_MODE = Compute
    MODE_NAME = Add Point
    XVAL = FME_CONDITIONAL:DEFAULT_VALUE''BOOL_OP;OR;COMPOSITE_TEST;1 OR 2;TEST @Value(_copynum) = 0;TEST @Value(_copynum) = 4'0'BOOL_OP;OR;COMPOSITE_TEST;1;TEST @Value(_copynum) = 1'1'BOOL_OP;OR;COMPOSITE_TEST;1;TEST @Value(_copynum) = 2'2'BOOL_OP;OR;COMPOSITE_TEST;1;TEST @Value(_copynum) = 3'1'FME_NUM_CONDITIONS5___
    YVAL = FME_CONDITIONAL:DEFAULT_VALUE''BOOL_OP;OR;COMPOSITE_TEST;1 OR 2;TEST @Value(_copynum) = 0;TEST @Value(_copynum) = 4'0'BOOL_OP;OR;COMPOSITE_TEST;1;TEST @Value(_copynum) = 1'2.5'BOOL_OP;OR;COMPOSITE_TEST;1;TEST @Value(_copynum) = 2'0'BOOL_OP;OR;COMPOSITE_TEST;1;TEST @Value(_copynum) = 3'0.8'FME_NUM_CONDITIONS5___
    -> LineBuilder_5
LineBuilder_5
    ACCUM_INPUT_ATTRS = Use Attributes From One Feature
    REMOVE_DUPLICATES = No
    POLYGON -> PDFStyler_6
PDFStyler_6
    COLOR = 0,0,0
    FILL_COLOR = 0,0,0
    FILL_OPACITY = 1.00
    FONT = MS Shell Dlg 2,12,BOLD
    LINE_CAP_STYLE_PARAM = Butt Cap
    LINE_DASH_PHASE = 0
    LINE_JOIN_STYLE_PARAM = Miter Join
    LINE_MITER_LIMIT = 0.0
    LINE_WIDTH = 1.5
    OPACITY = 1.0
    PDFStyled -> PDFPageFormatter [arrow]
Creator_2
    GEOMTYPE = Geometry Object
    NUM = 1
    CREATED -> AttributeManager_22
AttributeManager_22
    ATTR_TABLE = SET_TO BB_loc = $(Tile_num)
    -> VertexCreator_6
    -> VertexCreator_7
    -> VertexCreator_8
    -> VertexCreator_11
    -> VertexCreator_9
VertexCreator_6
    MEASURE_TYPE = Continuous
    MISSING_VAL_MODE = Compute
    MODE_NAME = Add Point
    XVAL = FME_CONDITIONAL:DEFAULT_VALUE''BOOL_OP;OR;COMPOSITE_TEST;1;TEST @Value(BB_loc) = 0'0'BOOL_OP;OR;COMPOSITE_TEST;1;TEST @Value(BB_loc) = 1'0'BOOL_OP;OR;COMPOSITE_TEST;1;TEST @Value(BB_loc) = 2'1'BOOL_OP;OR;COMPOSITE_TEST;1;TEST @Value(BB_loc) = 3'2'BOOL_OP;OR;COMPOSITE_TEST;1;TEST @Value(BB_loc) = 4'0'BOOL_OP;OR;COMPOSITE_TEST;1;TEST @Value(BB_loc) = 5'1'BOOL_OP;OR;COMPOSITE_TEST;1;TEST @Value(BB_loc) = 6'2'BOOL_OP;OR;COMPOSITE_TEST;1;TEST @Value(BB_loc) = 7'0'BOOL_OP;OR;COMPOSITE_TEST;1;TEST @Value(BB_loc) = 8'1'BOOL_OP;OR;COMPOSITE_TEST;1;TEST @Value(BB_loc) = 9'2'BOOL_OP;OR;COMPOSITE_TEST;1;TEST @Value(BB_loc) = 10'0'BOOL_OP;OR;COMPOSITE_TEST;1;TEST @Value(BB_loc) = 11'1'BOOL_OP;OR;COMPOSITE_TEST;1;TEST @Value(BB_loc) = 12'2'FME_NUM_CONDITIONS14___
    YVAL = FME_CONDITIONAL:DEFAULT_VALUE''BOOL_OP;OR;COMPOSITE_TEST;1;TEST @Value(BB_loc) = 0'4'BOOL_OP;OR;COMPOSITE_TEST;1;TEST @Value(BB_loc) = 1'4'BOOL_OP;OR;COMPOSITE_TEST;1;TEST @Value(BB_loc) = 2'4'BOOL_OP;OR;COMPOSITE_TEST;1;TEST @Value(BB_loc) = 3'4'BOOL_OP;OR;COMPOSITE_TEST;1;TEST @Value(BB_loc) = 4'3'BOOL_OP;OR;COMPOSITE_TEST;1;TEST @Value(BB_loc) = 5'3'BOOL_OP;OR;COMPOSITE_TEST;1;TEST @Value(BB_loc) = 6'3'BOOL_OP;OR;COMPOSITE_TEST;1;TEST @Value(BB_loc) = 7'2'BOOL_OP;OR;COMPOSITE_TEST;1;TEST @Value(BB_loc) = 8'2'BOOL_OP;OR;COMPOSITE_TEST;1;TEST @Value(BB_loc) = 9'2'BOOL_OP;OR;COMPOSITE_TEST;1;TEST @Value(BB_loc) = 10'1'BOOL_OP;OR;COMPOSITE_TEST;1;TEST @Value(BB_loc) = 11'1'BOOL_OP;OR;COMPOSITE_TEST;1;TEST @Value(BB_loc) = 12'1'FME_NUM_CONDITIONS14___
    -> LineBuilder_4
VertexCreator_7
    MEASURE_TYPE = Continuous
    MISSING_VAL_MODE = Compute
    MODE_NAME = Add Point
    XVAL = FME_CONDITIONAL:DEFAULT_VALUE''BOOL_OP;OR;COMPOSITE_TEST;1;TEST @Value(BB_loc) = 0'3'BOOL_OP;OR;COMPOSITE_TEST;1;TEST @Value(BB_loc) = 1'1'BOOL_OP;OR;COMPOSITE_TEST;1;TEST @Value(BB_loc) = 2'2'BOOL_OP;OR;COMPOSITE_TEST;1;TEST @Value(BB_loc) = 3'3'BOOL_OP;OR;COMPOSITE_TEST;1;TEST @Value(BB_loc) = 4'1'BOOL_OP;OR;COMPOSITE_TEST;1;TEST @Value(BB_loc) = 5'2'BOOL_OP;OR;COMPOSITE_TEST;1;TEST @Value(BB_loc) = 6'3'BOOL_OP;OR;COMPOSITE_TEST;1;TEST @Value(BB_loc) = 7'1'BOOL_OP;OR;COMPOSITE_TEST;1;TEST @Value(BB_loc) = 8'2'BOOL_OP;OR;COMPOSITE_TEST;1;TEST @Value(BB_loc) = 9'3'BOOL_OP;OR;COMPOSITE_TEST;1;TEST @Value(BB_loc) = 10'1'BOOL_OP;OR;COMPOSITE_TEST;1;TEST @Value(BB_loc) = 11'2'BOOL_OP;OR;COMPOSITE_TEST;1;TEST @Value(BB_loc) = 12'3'FME_NUM_CONDITIONS14___
    YVAL = FME_CONDITIONAL:DEFAULT_VALUE''BOOL_OP;OR;COMPOSITE_TEST;1;TEST @Value(BB_loc) = 0'4'BOOL_OP;OR;COMPOSITE_TEST;1;TEST @Value(BB_loc) = 1'4'BOOL_OP;OR;COMPOSITE_TEST;1;TEST @Value(BB_loc) = 2'4'BOOL_OP;OR;COMPOSITE_TEST;1;TEST @Value(BB_loc) = 3'4'BOOL_OP;OR;COMPOSITE_TEST;1;TEST @Value(BB_loc) = 4'3'BOOL_OP;OR;COMPOSITE_TEST;1;TEST @Value(BB_loc) = 5'3'BOOL_OP;OR;COMPOSITE_TEST;1;TEST @Value(BB_loc) = 6'3'BOOL_OP;OR;COMPOSITE_TEST;1;TEST @Value(BB_loc) = 7'2'BOOL_OP;OR;COMPOSITE_TEST;1;TEST @Value(BB_loc) = 8'2'BOOL_OP;OR;COMPOSITE_TEST;1;TEST @Value(BB_loc) = 9'2'BOOL_OP;OR;COMPOSITE_TEST;1;TEST @Value(BB_loc) = 10'1'BOOL_OP;OR;COMPOSITE_TEST;1;TEST @Value(BB_loc) = 11'1'BOOL_OP;OR;COMPOSITE_TEST;1;TEST @Value(BB_loc) = 12'1'FME_NUM_CONDITIONS14___
    -> LineBuilder_4
VertexCreator_8
    MEASURE_TYPE = Continuous
    MISSING_VAL_MODE = Compute
    MODE_NAME = Add Point
    XVAL = FME_CONDITIONAL:DEFAULT_VALUE''BOOL_OP;OR;COMPOSITE_TEST;1;TEST @Value(BB_loc) = 0'3'BOOL_OP;OR;COMPOSITE_TEST;1;TEST @Value(BB_loc) = 1'1'BOOL_OP;OR;COMPOSITE_TEST;1;TEST @Value(BB_loc) = 2'2'BOOL_OP;OR;COMPOSITE_TEST;1;TEST @Value(BB_loc) = 3'3'BOOL_OP;OR;COMPOSITE_TEST;1;TEST @Value(BB_loc) = 4'1'BOOL_OP;OR;COMPOSITE_TEST;1;TEST @Value(BB_loc) = 5'2'BOOL_OP;OR;COMPOSITE_TEST;1;TEST @Value(BB_loc) = 6'3'BOOL_OP;OR;COMPOSITE_TEST;1;TEST @Value(BB_loc) = 7'1'BOOL_OP;OR;COMPOSITE_TEST;1;TEST @Value(BB_loc) = 8'2'BOOL_OP;OR;COMPOSITE_TEST;1;TEST @Value(BB_loc) = 9'3'BOOL_OP;OR;COMPOSITE_TEST;1;TEST @Value(BB_loc) = 10'1'BOOL_OP;OR;COMPOSITE_TEST;1;TEST @Value(BB_loc) = 11'2'BOOL_OP;OR;COMPOSITE_TEST;1;TEST @Value(BB_loc) = 12'3'FME_NUM_CONDITIONS14___
    YVAL = FME_CONDITIONAL:DEFAULT_VALUE''BOOL_OP;OR;COMPOSITE_TEST;1;TEST @Value(BB_loc) = 0'0'BOOL_OP;OR;COMPOSITE_TEST;1;TEST @Value(BB_loc) = 1'3'BOOL_OP;OR;COMPOSITE_TEST;1;TEST @Value(BB_loc) = 2'3'BOOL_OP;OR;COMPOSITE_TEST;1;TEST @Value(BB_loc) = 3'3'BOOL_OP;OR;COMPOSITE_TEST;1;TEST @Value(BB_loc) = 4'2'BOOL_OP;OR;COMPOSITE_TEST;1;TEST @Value(BB_loc) = 5'2'BOOL_OP;OR;COMPOSITE_TEST;1;TEST @Value(BB_loc) = 6'2'BOOL_OP;OR;COMPOSITE_TEST;1;TEST @Value(BB_loc) = 7'1'BOOL_OP;OR;COMPOSITE_TEST;1;TEST @Value(BB_loc) = 8'1'BOOL_OP;OR;COMPOSITE_TEST;1;TEST @Value(BB_loc) = 9'1'BOOL_OP;OR;COMPOSITE_TEST;1;TEST @Value(BB_loc) = 10'0'BOOL_OP;OR;COMPOSITE_TEST;1;TEST @Value(BB_loc) = 11'0'BOOL_OP;OR;COMPOSITE_TEST;1;TEST @Value(BB_loc) = 12'0'FME_NUM_CONDITIONS14___
    -> LineBuilder_4
VertexCreator_11
    MEASURE_TYPE = Continuous
    MISSING_VAL_MODE = Compute
    MODE_NAME = Add Point
    XVAL = FME_CONDITIONAL:DEFAULT_VALUE''BOOL_OP;OR;COMPOSITE_TEST;1;TEST @Value(BB_loc) = 0'0'BOOL_OP;OR;COMPOSITE_TEST;1;TEST @Value(BB_loc) = 1'0'BOOL_OP;OR;COMPOSITE_TEST;1;TEST @Value(BB_loc) = 2'1'BOOL_OP;OR;COMPOSITE_TEST;1;TEST @Value(BB_loc) = 3'2'BOOL_OP;OR;COMPOSITE_TEST;1;TEST @Value(BB_loc) = 4'0'BOOL_OP;OR;COMPOSITE_TEST;1;TEST @Value(BB_loc) = 5'1'BOOL_OP;OR;COMPOSITE_TEST;1;TEST @Value(BB_loc) = 6'2'BOOL_OP;OR;COMPOSITE_TEST;1;TEST @Value(BB_loc) = 7'0'BOOL_OP;OR;COMPOSITE_TEST;1;TEST @Value(BB_loc) = 8'1'BOOL_OP;OR;COMPOSITE_TEST;1;TEST @Value(BB_loc) = 9'2'BOOL_OP;OR;COMPOSITE_TEST;1;TEST @Value(BB_loc) = 10'0'BOOL_OP;OR;COMPOSITE_TEST;1;TEST @Value(BB_loc) = 11'1'BOOL_OP;OR;COMPOSITE_TEST;1;TEST @Value(BB_loc) = 12'2'FME_NUM_CONDITIONS14___
    YVAL = FME_CONDITIONAL:DEFAULT_VALUE''BOOL_OP;OR;COMPOSITE_TEST;1;TEST @Value(BB_loc) = 0'0'BOOL_OP;OR;COMPOSITE_TEST;1;TEST @Value(BB_loc) = 1'3'BOOL_OP;OR;COMPOSITE_TEST;1;TEST @Value(BB_loc) = 2'3'BOOL_OP;OR;COMPOSITE_TEST;1;TEST @Value(BB_loc) = 3'3'BOOL_OP;OR;COMPOSITE_TEST;1;TEST @Value(BB_loc) = 4'2'BOOL_OP;OR;COMPOSITE_TEST;1;TEST @Value(BB_loc) = 5'2'BOOL_OP;OR;COMPOSITE_TEST;1;TEST @Value(BB_loc) = 6'2'BOOL_OP;OR;COMPOSITE_TEST;1;TEST @Value(BB_loc) = 7'1'BOOL_OP;OR;COMPOSITE_TEST;1;TEST @Value(BB_loc) = 8'1'BOOL_OP;OR;COMPOSITE_TEST;1;TEST @Value(BB_loc) = 9'1'BOOL_OP;OR;COMPOSITE_TEST;1;TEST @Value(BB_loc) = 10'0'BOOL_OP;OR;COMPOSITE_TEST;1;TEST @Value(BB_loc) = 11'0'BOOL_OP;OR;COMPOSITE_TEST;1;TEST @Value(BB_loc) = 12'0'FME_NUM_CONDITIONS14___
    -> LineBuilder_4
VertexCreator_9
    MEASURE_TYPE = Continuous
    MISSING_VAL_MODE = Compute
    MODE_NAME = Add Point
    XVAL = FME_CONDITIONAL:DEFAULT_VALUE''BOOL_OP;OR;COMPOSITE_TEST;1;TEST @Value(BB_loc) = 0'0'BOOL_OP;OR;COMPOSITE_TEST;1;TEST @Value(BB_loc) = 1'0'BOOL_OP;OR;COMPOSITE_TEST;1;TEST @Value(BB_loc) = 2'1'BOOL_OP;OR;COMPOSITE_TEST;1;TEST @Value(BB_loc) = 3'2'BOOL_OP;OR;COMPOSITE_TEST;1;TEST @Value(BB_loc) = 4'0'BOOL_OP;OR;COMPOSITE_TEST;1;TEST @Value(BB_loc) = 5'1'BOOL_OP;OR;COMPOSITE_TEST;1;TEST @Value(BB_loc) = 6'2'BOOL_OP;OR;COMPOSITE_TEST;1;TEST @Value(BB_loc) = 7'0'BOOL_OP;OR;COMPOSITE_TEST;1;TEST @Value(BB_loc) = 8'1'BOOL_OP;OR;COMPOSITE_TEST;1;TEST @Value(BB_loc) = 9'2'BOOL_OP;OR;COMPOSITE_TEST;1;TEST @Value(BB_loc) = 10'0'BOOL_OP;OR;COMPOSITE_TEST;1;TEST @Value(BB_loc) = 11'1'BOOL_OP;OR;COMPOSITE_TEST;1;TEST @Value(BB_loc) = 12'2'FME_NUM_CONDITIONS14___
    YVAL = FME_CONDITIONAL:DEFAULT_VALUE''BOOL_OP;OR;COMPOSITE_TEST;1;TEST @Value(BB_loc) = 0'4'BOOL_OP;OR;COMPOSITE_TEST;1;TEST @Value(BB_loc) = 1'4'BOOL_OP;OR;COMPOSITE_TEST;1;TEST @Value(BB_loc) = 2'4'BOOL_OP;OR;COMPOSITE_TEST;1;TEST @Value(BB_loc) = 3'4'BOOL_OP;OR;COMPOSITE_TEST;1;TEST @Value(BB_loc) = 4'3'BOOL_OP;OR;COMPOSITE_TEST;1;TEST @Value(BB_loc) = 5'3'BOOL_OP;OR;COMPOSITE_TEST;1;TEST @Value(BB_loc) = 6'3'BOOL_OP;OR;COMPOSITE_TEST;1;TEST @Value(BB_loc) = 7'2'BOOL_OP;OR;COMPOSITE_TEST;1;TEST @Value(BB_loc) = 8'2'BOOL_OP;OR;COMPOSITE_TEST;1;TEST @Value(BB_loc) = 9'2'BOOL_OP;OR;COMPOSITE_TEST;1;TEST @Value(BB_loc) = 10'1'BOOL_OP;OR;COMPOSITE_TEST;1;TEST @Value(BB_loc) = 11'1'BOOL_OP;OR;COMPOSITE_TEST;1;TEST @Value(BB_loc) = 12'1'FME_NUM_CONDITIONS14___
    -> LineBuilder_4
LineBuilder_4
    ACCUM_INPUT_ATTRS = Use Attributes From One Feature
    GROUP_BY = BB_loc
    REMOVE_DUPLICATES = No
    POLYGON -> PDFStyler_15
Creator
    GEOM = <?xml version="1.0" encoding="US_ASCII" standalone="no" ?><geometry><line><coord x="0" y="4"/><coord x="3" y="4"/><coord x="3" y="0"/><coord x="0" y="0"/><coord x="0" y="4"/><coord x="1" y="4"/><coord x="1" y="0"/><coord x="2" y="0"/><coord x="2" y="4"/><coord x="3" y="4"/><coord x="3" y="3"/><coord x="0" y="3"/><coord x="0" y="2"/><coord x="3" y="2"/><coord x="3" y="1"/><coord x="0" y="1"/></line></geometry>
    GEOMTYPE = Geometry Object
    NUM = 1
    CREATED -> PDFStyler_15
PDFStyler_15
    COLOR = 0,0,0
    FILL_COLOR = 0,0.333333,1
    FILL_OPACITY = 0.51
    FONT = MS Shell Dlg 2,12,BOLD
    LINE_CAP_STYLE_PARAM = Butt Cap
    LINE_DASH_PHASE = 0
    LINE_JOIN_STYLE_PARAM = Miter Join
    LINE_MITER_LIMIT = 0.0
    LINE_WIDTH = 1.5
    OPACITY = 1.0
    PDFStyled -> PDFPageFormatter [tabular]
North_2: Creator
    GEOM = <?xml version="1.0" encoding="US_ASCII" standalone="no" ?><geometry><text><point><coord x="0" y="0"/></point><textString>null</textString><textSize>10</textSize><textRotation>0</textRotation></text></geometry>
    GEOMTYPE = Geometry Object
    NUM = 1
    CREATED -> AttributeManager_23
AttributeManager_23
    ATTR_TABLE:
      SET_TO BB_loc = $(Tile_num)
      SET_TO fme_text_string = FME_CONDITIONAL:DEFAULT_VALUE'_FME_NO_OP_'BOOL_OP;OR;COMPOSITE_TEST;1;TEST @Value(BB_loc) = 0'Full BoundingBox'BOOL_OP;OR;COMPOSITE_TEST;1;TEST @Value(BB_loc) = 1'Sub-tile n° (0,3)'BOOL_OP;OR;COMPOSITE_TEST;1;TEST @Value(BB_loc) = 2'Sub-tile n° (1,3)'BOOL_OP;OR;COMPOSITE_TEST;1;TEST @Value(BB_loc) = 3'Sub-tile n° (2,3)'BOOL_OP;OR;COMPOSITE_TEST;1;TEST @Value(BB_loc) = 4'Sub-tile n° (0,2)'BOOL_OP;OR;COMPOSITE_TEST;1;TEST @Value(BB_loc) = 5'Sub-tile n° (1,2)'BOOL_OP;OR;COMPOSITE_TEST;1;TEST @Value(BB_loc) = 6'Sub-tile n° (2,2)'BOOL_OP;OR;COMPOSITE_TEST;1;TEST @Value(BB_loc) = 7'Sub-tile n° (0,1)'BOOL_OP;OR;COMPOSITE_TEST;1;TEST @Value(BB_loc) = 8'Sub-tile n° (1,1)'BOOL_OP;OR;COMPOSITE_TEST;1;TEST @Value(BB_loc) = 9'Sub-tile n° (2,1)'BOOL_OP;OR;COMPOSITE_TEST;1;TEST @Value(BB_loc) = 10'Sub-tile n° (0,0)'BOOL_OP;OR;COMPOSITE_TEST;1;TEST @Value(BB_loc) = 11'Sub-tile n° (1,0)'BOOL_OP;OR;COMPOSITE_TEST;1;TEST @Value(BB_loc) = 12'Sub-tile n° (2,0)'FME_NUM_CONDITIONS14___
    -> PDFStyler_16
PDFStyler_16
    COLOR = 0,0.333333,1
    FILL_COLOR = 0,0.333333,1
    FILL_OPACITY = 1.00
    FONT = MS Shell Dlg 2,12,BOLD
    LINE_CAP_STYLE_PARAM = Butt Cap
    LINE_DASH_PHASE = 0
    LINE_JOIN_STYLE_PARAM = Miter Join
    LINE_MITER_LIMIT = 0.0
    LINE_WIDTH = 1.5
    OPACITY = 1.0
    PDFStyled -> PDFPageFormatter [coord]
Creator_4
    GEOMTYPE = Geometry Object
    NUM = 1
    CREATED -> Cloner_6
Cloner_6
    COPIES = 5
    COPYATT = _copynum
    COPY -> VertexCreator_3
VertexCreator_3
    MEASURE_TYPE = Continuous
    MISSING_VAL_MODE = Compute
    MODE_NAME = Add Point
    XVAL = FME_CONDITIONAL:DEFAULT_VALUE''BOOL_OP;OR;COMPOSITE_TEST;1 OR 2;TEST @Value(_copynum) = 0;TEST @Value(_copynum) = 4'0'BOOL_OP;OR;COMPOSITE_TEST;1;TEST @Value(_copynum) = 1'0'BOOL_OP;OR;COMPOSITE_TEST;1;TEST @Value(_copynum) = 2'8'BOOL_OP;OR;COMPOSITE_TEST;1;TEST @Value(_copynum) = 3'8'FME_NUM_CONDITIONS5___
    YVAL = FME_CONDITIONAL:DEFAULT_VALUE''BOOL_OP;OR;COMPOSITE_TEST;1 OR 2;TEST @Value(_copynum) = 0;TEST @Value(_copynum) = 4'0'BOOL_OP;OR;COMPOSITE_TEST;1;TEST @Value(_copynum) = 1'1'BOOL_OP;OR;COMPOSITE_TEST;1;TEST @Value(_copynum) = 2'1'BOOL_OP;OR;COMPOSITE_TEST;1;TEST @Value(_copynum) = 3'0'FME_NUM_CONDITIONS5___
    -> LineBuilder_6
LineBuilder_6
    ACCUM_INPUT_ATTRS = Use Attributes From One Feature
    REMOVE_DUPLICATES = No
    POLYGON -> Cloner
Cloner
    COPIES = 2
    COPYATT = _copynum
    COPY -> TestFilter_2
TestFilter_2
    DEFAULT_VALUE = right
    TEST_LIST = "BOOL_OP,OR,COMPOSITE_TEST,""""""1"""""",TEST_CLAUSE,TEST @Value(_copynum) = 0",left
    left -> PDFStyler_9
    right -> PDFStyler_10
PDFStyler_9
    COLOR = 0,0,0
    FILL_COLOR = 1,1,1
    FILL_OPACITY = 1.00
    FONT = MS Shell Dlg 2,12,BOLD
    LINE_CAP_STYLE_PARAM = Butt Cap
    LINE_DASH_PHASE = 0
    LINE_JOIN_STYLE_PARAM = Miter Join
    LINE_MITER_LIMIT = 0.0
    LINE_WIDTH = 2
    OPACITY = 1.0
    PDFStyled -> PDFPageFormatter [left_scale]
PDFStyler_10
    COLOR = 0,0,0
    FILL_COLOR = 0,0,0
    FILL_OPACITY = 1.00
    FONT = MS Shell Dlg 2,12,BOLD
    LINE_CAP_STYLE_PARAM = Butt Cap
    LINE_DASH_PHASE = 0
    LINE_JOIN_STYLE_PARAM = Miter Join
    LINE_MITER_LIMIT = 0.0
    LINE_WIDTH = 2
    OPACITY = 1.0
    PDFStyled -> PDFPageFormatter [right_scale]
Note: Set the page size and add 'Title', 'Main' and 'Signature' frames. / To control the feature type order in the output 'Layer', they must / be ordered by how they should be drawn using the sorter transformer. / NOTE: All feature types that overlap must be considered in the / same frame (drawing object) or the scale and bounds will not match.
PDFPageFormatter
    PAGE_HEIGHT_PTS = 612
    PAGE_HEIGHT_USER = 8.5
    PAGE_NUMBER = 1
    PAGE_OBJECTS = "left_scale WIDTH;68.4;FIXED_ASPECT;Yes;MINX;586.8;SIZE_PARAMS;;HEIGHT;21.6;SCALING_PARAMS;;MINY;140.4;CLIPPING_ENABLED;No","right_scale WIDTH;68.4;FIXED_ASPECT;Yes;MINX;655.92;SIZE_PARAMS;;HEIGHT;21.6;SCALING_PARAMS;;MINY;140.4;CLIPPING_ENABLED;No","Scale 1 WIDTH;36;FIXED_ASPECT;Yes;MINX;702;SIZE_PARAMS;;HEIGHT;14.4;SCALING_PARAMS;;MINY;123.84;CLIPPING_ENABLED;No","Signature_Frame WIDTH;198;FIXED_ASPECT;Yes;MINX;588.119;SIZE_PARAMS;;HEIGHT;20;SCALING_PARAMS;;MINY;6.36556;CLIPPING_ENABLED;No","Title_Frame WIDTH;219.47;FIXED_ASPECT;Yes;MINX;20.4792;SIZE_PARAMS;;HEIGHT;20;SCALING_PARAMS;;MINY;578.035;CLIPPING_ENABLED;No","Main WIDTH;540;FIXED_ASPECT;Yes;MINX;22.32;SIZE_PARAMS;;HEIGHT;540;SCALING_PARAMS;;MINY;28.08;CLIPPING_ENABLED;No","Scale 2 WIDTH;36;FIXED_ASPECT;Yes;MINX;635.76;SIZE_PARAMS;;HEIGHT;14.4;SCALING_PARAMS;;MINY;123.84;CLIPPING_ENABLED;No","Scale 3 WIDTH;36;FIXED_ASPECT;Yes;MINX;568.08;SIZE_PARAMS;;HEIGHT;14.4;SCALING_PARAMS;;MINY;123.84;CLIPPING_ENABLED;No","North WIDTH;14.4;FIXED_ASPECT;Yes;MINX;648;SIZE_PARAMS;;HEIGHT;14.4;SCALING_PARAMS;;MINY;259.2;CLIPPING_ENABLED;No","tabular WIDTH;144.72;FIXED_ASPECT;Yes;MINX;587.58;SIZE_PARAMS;;HEIGHT;166.32;SCALING_PARAMS;;MINY;320.409;CLIPPING_ENABLED;No","coord WIDTH;138.96;FIXED_ASPECT;Yes;MINX;594.771;SIZE_PARAMS;;HEIGHT;47.52;SCALING_PARAMS;;MINY;478.477;CLIPPING_ENABLED;No","arrow WIDTH;57.6;FIXED_ASPECT;Yes;MINX;626.4;SIZE_PARAMS;;HEIGHT;52.56;SCALING_PARAMS;;MINY;199.44;CLIPPING_ENABLED;No"
    PAGE_ORIENTATION = Landscape
    PAGE_SIZE = Letter
    PAGE_UNITS = Inches
    PAGE_WIDTH_PTS = 792
    PAGE_WIDTH_USER = 11
    -> JPEG2000 (writer PDF2D_2)
JPEG2000 (writer PDF2D_2)

Bookmark: Scale
AttributeManager_7 [off]
    ATTR_TABLE:
      SET_TO arrow1x = @Evaluate($(Coord_LR_x)-(@Value(_indices{1}.x)-@Value(_indices{0}.x))*0.15)
      SET_TO arrow1y = @Evaluate(@sub($(Coord_LR_y),@mult((@Value(_indices{1}.x)-@Value(_indices{0}.x))*0.015,@cos(@mult(@pi(),0.555555555,$(Coord_LR_y))))))
      SET_TO arrow2x = @Evaluate($(Coord_LR_x)-(@Value(_indices{1}.x)-@Value(_indices{0}.x))*0.15)
      SET_TO arrow2y = @Evaluate(@sub($(Coord_LR_y),@mult((@Value(_indices{1}.x)-@Value(_indices{0}.x))*0.035,@cos(@mult(@pi(),0.555555555,$(Coord_LR_y))))))
      SET_TO arrow3x = @Evaluate($(Coord_LR_x)-(@Value(_indices{1}.x)-@Value(_indices{0}.x))*0.3)
      SET_TO arrow3y = @Evaluate(@sub($(Coord_LR_y),@mult((@Value(_indices{1}.x)-@Value(_indices{0}.x))*0.035,@cos(@mult(@pi(),0.555555555,$(Coord_LR_y))))))
      SET_TO arrow4x = @Evaluate($(Coord_LR_x)-(@Value(_indices{1}.x)-@Value(_indices{0}.x))*0.3)
      SET_TO arrow4y = @Evaluate(@sub($(Coord_LR_y),@mult((@Value(_indices{1}.x)-@Value(_indices{0}.x))*0.015,@cos(@mult(@pi(),0.555555555,$(Coord_LR_y))))))
    -> Cloner_3
Cloner_3 [off]
    COPIES = 5
    COPYATT = _copynum
    COPY -> AttributeManager_8
AttributeManager_8 [off]
    ATTR_TABLE:
      SET_TO x = FME_CONDITIONAL:DEFAULT_VALUE'_FME_NO_OP_'BOOL_OP;OR;COMPOSITE_TEST;1;TEST @Value(_copynum) = 0'@Value(arrow1x)'BOOL_OP;OR;COMPOSITE_TEST;1;TEST @Value(_copynum) = 1'@Value(arrow2x)'BOOL_OP;OR;COMPOSITE_TEST;1;TEST @Value(_copynum) = 2'@Value(arrow3x)'BOOL_OP;OR;COMPOSITE_TEST;1;TEST @Value(_copynum) = 3'@Value(arrow4x)'BOOL_OP;OR;COMPOSITE_TEST;1;TEST @Value(_copynum) = 4'@Value(arrow1x)'FME_NUM_CONDITIONS6___
      SET_TO y = FME_CONDITIONAL:DEFAULT_VALUE'_FME_NO_OP_'BOOL_OP;OR;COMPOSITE_TEST;1;TEST @Value(_copynum) = 0'@Value(arrow1y)'BOOL_OP;OR;COMPOSITE_TEST;1;TEST @Value(_copynum) = 1'@Value(arrow2y)'BOOL_OP;OR;COMPOSITE_TEST;1;TEST @Value(_copynum) = 2'@Value(arrow3y)'BOOL_OP;OR;COMPOSITE_TEST;1;TEST @Value(_copynum) = 3'@Value(arrow4y)'BOOL_OP;OR;COMPOSITE_TEST;1;TEST @Value(_copynum) = 4'@Value(arrow1y)'FME_NUM_CONDITIONS6___
    -> AttributeManager_9
AttributeManager_9 [off]
    ATTR_TABLE:
      REMOVE _indices{}.x
      REMOVE _indices{}.y
      REMOVE _indices{}.z
      REMOVE arrow1x
      REMOVE arrow1y
      REMOVE arrow2x
      REMOVE arrow2y
      REMOVE arrow3x
      REMOVE arrow3y
      REMOVE arrow4x
      REMOVE arrow4y
    -> GeometryRemover_3
GeometryRemover_3 [off]
    -> VertexCreator_4
VertexCreator_4 [off]
    MEASURE_TYPE = Continuous
    MISSING_VAL_MODE = Compute
    MODE_NAME = Add Point
    XVAL = @Value(x)
    YVAL = @Value(y)
    -> LineBuilder_3
AttributeManager_4 [off]
    ATTR_TABLE:
      SET_TO arrow1x = @Evaluate($(Coord_LR_x))
      SET_TO arrow1y = @Evaluate(@sub($(Coord_LR_y),@mult((@Value(_indices{1}.x)-@Value(_indices{0}.x))*0.015,@cos(@mult(@pi(),0.555555555,$(Coord_LR_y))))))
      SET_TO arrow2x = @Evaluate($(Coord_LR_x))
      SET_TO arrow2y = @Evaluate(@Evaluate(@sub($(Coord_LR_y),@mult((@Value(_indices{1}.x)-@Value(_indices{0}.x))*0.035,@cos(@mult(@pi(),0.555555555,$(Coord_LR_y)))))))
      SET_TO arrow3x = @Evaluate($(Coord_LR_x)-(@Value(_indices{1}.x)-@Value(_indices{0}.x))*0.15)
      SET_TO arrow3y = @Evaluate(@Evaluate(@sub($(Coord_LR_y),@mult((@Value(_indices{1}.x)-@Value(_indices{0}.x))*0.035,@cos(@mult(@pi(),0.555555555,$(Coord_LR_y)))))))
      SET_TO arrow4x = @Evaluate($(Coord_LR_x)-(@Value(_indices{1}.x)-@Value(_indices{0}.x))*0.15)
      SET_TO arrow4y = @Evaluate(@sub($(Coord_LR_y),@mult((@Value(_indices{1}.x)-@Value(_indices{0}.x))*0.015,@cos(@mult(@pi(),0.555555555,$(Coord_LR_y))))))
    -> Cloner_2
Cloner_2 [off]
    COPIES = 5
    COPYATT = _copynum
    COPY -> AttributeManager_5
AttributeManager_5 [off]
    ATTR_TABLE:
      SET_TO x = FME_CONDITIONAL:DEFAULT_VALUE'_FME_NO_OP_'BOOL_OP;OR;COMPOSITE_TEST;1;TEST @Value(_copynum) = 0'@Value(arrow1x)'BOOL_OP;OR;COMPOSITE_TEST;1;TEST @Value(_copynum) = 1'@Value(arrow2x)'BOOL_OP;OR;COMPOSITE_TEST;1;TEST @Value(_copynum) = 2'@Value(arrow3x)'BOOL_OP;OR;COMPOSITE_TEST;1;TEST @Value(_copynum) = 3'@Value(arrow4x)'BOOL_OP;OR;COMPOSITE_TEST;1;TEST @Value(_copynum) = 4'@Value(arrow1x)'FME_NUM_CONDITIONS6___
      SET_TO y = FME_CONDITIONAL:DEFAULT_VALUE'_FME_NO_OP_'BOOL_OP;OR;COMPOSITE_TEST;1;TEST @Value(_copynum) = 0'@Value(arrow1y)'BOOL_OP;OR;COMPOSITE_TEST;1;TEST @Value(_copynum) = 1'@Value(arrow2y)'BOOL_OP;OR;COMPOSITE_TEST;1;TEST @Value(_copynum) = 2'@Value(arrow3y)'BOOL_OP;OR;COMPOSITE_TEST;1;TEST @Value(_copynum) = 3'@Value(arrow4y)'BOOL_OP;OR;COMPOSITE_TEST;1;TEST @Value(_copynum) = 4'@Value(arrow1y)'FME_NUM_CONDITIONS6___
    -> AttributeManager_6
AttributeManager_6 [off]
    ATTR_TABLE:
      REMOVE _indices{}.x
      REMOVE _indices{}.y
      REMOVE _indices{}.z
      REMOVE arrow1x
      REMOVE arrow1y
      REMOVE arrow2x
      REMOVE arrow2y
      REMOVE arrow3x
      REMOVE arrow3y
      REMOVE arrow4x
      REMOVE arrow4y
    -> GeometryRemover_2
GeometryRemover_2 [off]
    -> VertexCreator_2
VertexCreator_2 [off]
    MEASURE_TYPE = Continuous
    MISSING_VAL_MODE = Compute
    MODE_NAME = Add Point
    XVAL = @Value(x)
    YVAL = @Value(y)
    -> LineBuilder_2
