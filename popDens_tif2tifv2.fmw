FME workspace popDens_tif2tifv2.fmw

Parameters:
- SourceDataset_GEOTIFF = $(FME_MF_DIR)EXEL_FILES\ppp_2020_1km_Aggregated.tif   # Source GeoTIFF File(s)
- DestDataset_GEOTIFF = $(FME_MF_DIR)output_$(ISO_code)\03_Population_Density   # Destination GeoTIFF Folder
- DestDataset_TEXTLINE = $(FME_MF_DIR)output_$(ISO_code)\03_Population_density\pop_dens_BB.txt   # Destination Text File
- ISO_code = CHE   # Choose ISO_code for country
- GEOM = -0.46 51.38 0.11 51.67   # Select bounding box

Readers:
- GEOTIFF_1: GEOTIFF from $(SourceDataset_GEOTIFF)

Writers:
- GEOTIFF_2: GEOTIFF to $(DestDataset_GEOTIFF)
- TEXTLINE_1: TEXTLINE to $(DestDataset_TEXTLINE)

Creator
    COORDS = $(GEOM)
    COORDSYS = LL-WGS84
    GEOMTYPE = 2D Min/Max Box
    NUM = 1
    CREATED -> Clipper [CLIPPER]
Clipper
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clipper Only
    INSIDE -> GEOTIFF (writer GEOTIFF_2)
    INSIDE -> RasterStatisticsCalculator
RasterStatisticsCalculator
    RASTER_LEVEL = BAND_ONLY
    RASTER_STATS = "0   MEAN     "
    -> AttributeManager
AttributeManager
    ATTR_TABLE:
      REMOVE _creation_instance
      REMOVE fme_basename
      REMOVE _clipped
      RENAME_SET_VALUE band0.mean > text_line_data
    -> text_line (writer TEXTLINE_1)
text_line (writer TEXTLINE_1)
    attributes: text_line_data buffer

Bookmark: Reader Feature Types
GEOTIFF (reader GEOTIFF_1)
    -> Clipper [CLIPPEE]

Bookmark: Writer Feature Types
GEOTIFF (writer GEOTIFF_2)
