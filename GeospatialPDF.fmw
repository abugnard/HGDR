FME workspace GeospatialPDF.fmw
Title: Geospatial PDF - Cartographic Output

Parameters:
- SourceDataset_JPEG2000 = $(FME_MF_DIR)output__CH_CH_CH\04_Basemap\basemap__CH_CH_CH.jp2   # Source JPEG 2000 File(s)
- Zoom = 12   # Zoom of the basemap
- Coord_LR_x = 6.9554412537493135   # Coordinates lower right corner
- Coord_LR_y = 46.38397689820716   # Coordinates lower right corner
- FILE_name = BoundingBox   # Choose filename
- Layer_1 = $(FME_MF_DIR)output__CH_CH_CH\waterway\20220613__CH_CH_CH_waterway_line.shp   # Destination of the layer to map
- Layer_2 = $(FME_MF_DIR)output__CH_CH_CH\highway\20220613__CH_CH_CH_highway_line.shp   # Destination of the layer to map
- DestDataset_PDF2D = $(FME_MF_DIR)output__CH_CH_CH\05_export_PDF\export_PDF.pdf   # Destination Adobe Geospatial PDF File

Readers:
- JPEG2000_1: JPEG2000 from $(SourceDataset_JPEG2000) in LL-WGS84
- PDF2D_1: PDF2D from $(FME_MF_DIR)PDF_legend.pdf

Writers:
- PDF2D_2: PDF2D to $(DestDataset_PDF2D)

JPEG2000 (reader JPEG2000_1)
    -> BoundingBoxAccumulator
    -> AttributeCreator
AttributeCreator
    ATTR_TABLE:
      SET_TO _order = 0
      SET_TO fme_feature_type = BackgroundMap
    -> Sorter
BoundingBoxAccumulator
    ACCUM_ATTRS_NAME = Use Attributes From One Feature
    BOUNDING_BOX -> AttributeCreator_2
    BOUNDING_BOX -> Clipper [CLIPPER]
    BOUNDING_BOX -> Clipper_2 [CLIPPER]
    BOUNDING_BOX -> CoordinateExtractor
AttributeCreator_2
    ATTR_TABLE:
      SET_TO _order = 1
      SET_TO fme_feature_type = BoundingBox
    -> PDFStyler_3
PDFStyler_3
    COLOR = 0,0,0
    FILL_COLOR = 0,0,0
    FILL_OPACITY = 0
    FONT = Helvetica,9
    LINE_CAP_STYLE_PARAM = Butt Cap
    LINE_DASH_PHASE = 0
    LINE_JOIN_STYLE_PARAM = Miter Join
    LINE_MITER_LIMIT = 0.0
    LINE_WIDTH = 3
    OPACITY = 1.0
    PDFStyled -> Sorter
CoordinateExtractor
    LIST_NAME = _indices
    MODE = All Coordinates
    -> AttributeManager
    -> AttributeManager_4
    -> AttributeManager_7
    -> AttributeManager_10
LineBuilder_3
    ACCUM_INPUT_ATTRS = Use Attributes From One Feature
    GROUP_BY = fme_basename
    REMOVE_DUPLICATES = No
    POLYGON -> AttributeCreator_6
AttributeCreator_6
    ATTR_TABLE:
      SET_TO _order = 6
      SET_TO pdf_point_width = 1.5
    -> PDFStyler_7
PDFStyler_7
    COLOR = 0,0,0
    FILL_COLOR = 1,1,1
    FILL_OPACITY = 1.00
    FONT = Helvetica,14,ITALIC
    LINE_CAP_STYLE_PARAM = Butt Cap
    LINE_DASH_PHASE = 0
    LINE_JOIN_STYLE_PARAM = Miter Join
    LINE_MITER_LIMIT = 0.0
    LINE_WIDTH = 3
    OPACITY = 1.00
    PDFStyled -> Sorter
LineBuilder_2
    ACCUM_INPUT_ATTRS = Use Attributes From One Feature
    GROUP_BY = fme_basename
    REMOVE_DUPLICATES = No
    POLYGON -> AttributeCreator_7
AttributeCreator_7
    ATTR_TABLE = SET_TO _order = 7
    -> PDFStyler_8
PDFStyler_8
    COLOR = 0,0,0
    FILL_COLOR = 0,0,0
    FILL_OPACITY = 1.00
    FONT = Helvetica,0.1,ITALIC
    LINE_CAP_STYLE_PARAM = Butt Cap
    LINE_DASH_PHASE = 0
    LINE_JOIN_STYLE_PARAM = Miter Join
    LINE_MITER_LIMIT = 0.0
    LINE_WIDTH = 3
    OPACITY = 1.00
    PDFStyled -> Sorter
AttributeManager_10
    ATTR_TABLE:
      SET_TO arrow1x = @Evaluate($(Coord_LR_x)-(@Value(_indices{1}.x)-@Value(_indices{0}.x))*0.147)
      SET_TO arrow1y = $(Coord_LR_y)
      SET_TO arrow2x = @Evaluate($(Coord_LR_x)-(@Value(_indices{1}.x)-@Value(_indices{0}.x))*0.55)
      SET_TO arrow2y = $(Coord_LR_y)
      SET_TO dist = @Evaluate(@abs(@Value(arrow1x)-@Value(arrow2x)))
    -> Cloner_4
AttributeCreator_5
    ATTR_TABLE:
      SET_TO _order = 8
      SET_TO pdf_point_width = 1.5
    -> PDFStyler_6
PDFStyler_6
    COLOR = 0,0,0
    FILL_COLOR = 0,0,0
    FILL_OPACITY = 0.4
    FONT = Helvetica,0.03,ITALIC
    LINE_CAP_STYLE_PARAM = Butt Cap
    LINE_DASH_PHASE = 0
    LINE_JOIN_STYLE_PARAM = Miter Join
    LINE_MITER_LIMIT = 0.0
    LINE_WIDTH = 0.8
    OPACITY = 1.0
    PDFStyled -> Sorter
LineBuilder
    ACCUM_INPUT_ATTRS = Use Attributes From One Feature
    GROUP_BY = fme_basename
    REMOVE_DUPLICATES = No
    POLYGON -> AttributeCreator_8
AttributeCreator_8
    ATTR_TABLE = SET_TO _order = 7
    -> PDFStyler_9
PDFStyler_9
    COLOR = 1,1,1
    FILL_COLOR = 0,0,0
    FILL_OPACITY = 1.00
    FONT = Helvetica,0.1,ITALIC
    LINE_CAP_STYLE_PARAM = Butt Cap
    LINE_DASH_PHASE = 0
    LINE_JOIN_STYLE_PARAM = Miter Join
    LINE_MITER_LIMIT = 0.0
    LINE_WIDTH = 1.5
    OPACITY = 1.00
    PDFStyled -> Sorter
Creator_5
    GEOMTYPE = Geometry Object
    NUM = 1
    CREATED -> FeatureReader_2 [INITIATOR]
    CREATED -> FeatureReader [INITIATOR]
FeatureReader_2
    ATTR_ACCUM_MODE = Only Use Result
    COMBINE_GEOM = Use Result
    DATASET = $(Layer_1)
    FORMAT = SHAPEFILE
    INTERACT = <No Spatial Filter>
    OUTPUT_FEATURES_DISPLAY = Schema and Data Features
    SHAPEFILE_DONUT_DETECTION = ORIENTATION
    SHAPEFILE_ENCODING = fme-source-encoding
    SHAPEFILE_MEASURES_AS_Z = No
    SHAPEFILE_NUMERIC_TYPE_ATTRIBUTE_HANDLING = STANDARD_TYPES
    SHAPEFILE_READ_BLANK_AS = MISSING
    SHAPEFILE_REPORT_BAD_GEOMETRY = No
    SHAPEFILE_TRIM_PRECEDING_SPACES = Yes
    SHAPEFILE_USE_SEARCH_ENVELOPE = NO
    <OTHER> -> Clipper_2 [CLIPPEE]
Clipper_2
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    INSIDE -> AttributeCreator_4
AttributeCreator_4
    ATTR_TABLE:
      SET_TO _order = 3
      SET_TO pdf_point_width = 1.5
    -> PDFStyler_5
PDFStyler_5
    COLOR = 0,0,1
    FILL_COLOR = 0,0,1
    FILL_OPACITY = 0.4
    FONT = Helvetica,14,ITALIC
    LINE_CAP_STYLE_PARAM = Butt Cap
    LINE_DASH_PHASE = 0
    LINE_JOIN_STYLE_PARAM = Miter Join
    LINE_MITER_LIMIT = 0.0
    LINE_WIDTH = 2
    OPACITY = 1.0
    PDFStyled -> Sorter
FeatureReader
    ATTRIBUTES = 20220609_BS_highway_line,"addr:house,addr:stree,admin_leve,aerialway,aeroway,amenity,barrier,boundary,building,bus,craft,electrifie,emergency,fire_hydra,fire_hyd00,fire_hyd01,fme_geomet,fme_geom00,fme_geom01,fme_geom02,fme_geom03,gauge,geological,highway,historic,informatio,landuse,leisure,man_made,military,name,natural,network,office,place,power,public_tra,railway,ref,route,shop,source,sport,tourism,type,waterway,name:en,official_n,wikidata,according_,accordin00,accordin01,accordin02,accordin03,accordin04,accordin05"
    ATTR_ACCUM_MODE = Only Use Result
    COMBINE_GEOM = Use Result
    DATASET = $(Layer_2)
    FORMAT = SHAPEFILE
    INTERACT = <No Spatial Filter>
    OUTPUT_FEATURES_DISPLAY = Schema and Data Features
    SHAPEFILE_DONUT_DETECTION = ORIENTATION
    SHAPEFILE_ENCODING = fme-source-encoding
    SHAPEFILE_MEASURES_AS_Z = No
    SHAPEFILE_NUMERIC_TYPE_ATTRIBUTE_HANDLING = STANDARD_TYPES
    SHAPEFILE_READ_BLANK_AS = MISSING
    SHAPEFILE_REPORT_BAD_GEOMETRY = No
    SHAPEFILE_TRIM_PRECEDING_SPACES = Yes
    SHAPEFILE_USE_SEARCH_ENVELOPE = NO
    <OTHER> -> Clipper [CLIPPEE]
Clipper
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    INSIDE -> AttributeCreator_3
AttributeCreator_3
    ATTR_TABLE = SET_TO _order = 2
    -> PDFStyler_4
PDFStyler_4
    COLOR = 1,0.333333,0
    FILL_COLOR = 1,0.333333,0
    FILL_OPACITY = 1.00
    FONT = Helvetica,9
    LINE_CAP_STYLE_PARAM = Butt Cap
    LINE_DASH_PHASE = 0
    LINE_JOIN_STYLE_PARAM = Miter Join
    LINE_MITER_LIMIT = 0.0
    LINE_WIDTH = 1
    OPACITY = 1.0
    PDFStyled -> Sorter
Note: Sort drawing order with _order
Sorter
    SORT_PARM = _order NUMERIC ASCENDING
    SORTED -> PDFPageFormatter [Main]
Title: Creator
    GEOM = <?xml version="1.0" encoding="US_ASCII" standalone="no" ?><geometry><text><point><coord x="0" y="0"/></point><textString>Cartographic output</textString><textSize>1</textSize><textRotation>0</textRotation></text></geometry>
    GEOMTYPE = Geometry Object
    NUM = 1
    CREATED -> PDFStyler
PDFStyler
    COLOR = 0,0,0
    FILL_COLOR = 0,0,0
    FILL_OPACITY = 0.4
    FONT = Helvetica,13
    LINE_CAP_STYLE_PARAM = Butt Cap
    LINE_DASH_PHASE = 0
    LINE_JOIN_STYLE_PARAM = Miter Join
    LINE_MITER_LIMIT = 0.0
    LINE_WIDTH = 1.0
    OPACITY = 1.0
    PDFStyled -> PDFPageFormatter [Title_Frame]
Signature: Creator
    GEOM = <?xml version="1.0" encoding="US_ASCII" standalone="no" ?><geometry><text><point><coord x="0" y="0"/></point><textString>HGDR project, INSER SA</textString><textSize>10</textSize><textRotation>0</textRotation></text></geometry>
    GEOMTYPE = Geometry Object
    NUM = 1
    CREATED -> PDFStyler_2
PDFStyler_2
    COLOR = 0,0,0
    FILL_COLOR = 0,0,0
    FILL_OPACITY = 0.4
    FONT = Helvetica,8,ITALIC
    LINE_CAP_STYLE_PARAM = Butt Cap
    LINE_DASH_PHASE = 0
    LINE_JOIN_STYLE_PARAM = Miter Join
    LINE_MITER_LIMIT = 0.0
    LINE_WIDTH = 1.0
    OPACITY = 1.0
    PDFStyled -> PDFPageFormatter [Signature_Frame]
Note: Set the page size and add 'Title', 'Main' and 'Signature' frames. / To control the feature type order in the output 'Layer', they must / be ordered by how they should be drawn using the sorter transformer. / NOTE: All feature types that overlap must be considered in the / same frame (drawing object) or the scale and bounds will not match.
PDFPageFormatter
    PAGE_HEIGHT_PTS = 612
    PAGE_HEIGHT_USER = 8.5
    PAGE_NUMBER = 1
    PAGE_OBJECTS = "Title_Frame SIZE_PARAMS;;MINY;575.879;FIXED_ASPECT;Yes;CLIPPING_ENABLED;No;MINX;16.1868;WIDTH;324;HEIGHT;22.86;SCALING_PARAMS;","Signature_Frame SIZE_PARAMS;;MINY;6.36551;FIXED_ASPECT;Yes;CLIPPING_ENABLED;No;MINX;569.795;WIDTH;198;HEIGHT;20;SCALING_PARAMS;","Main SIZE_PARAMS;;MINY;32.673;FIXED_ASPECT;Yes;CLIPPING_ENABLED;No;MINX;18.0606;WIDTH;747.43;HEIGHT;533.48;SCALING_PARAMS;"
    PAGE_ORIENTATION = Landscape
    PAGE_SIZE = Letter
    PAGE_UNITS = Inches
    PAGE_WIDTH_PTS = 792
    PAGE_WIDTH_USER = 11
    -> JPEG2000 (writer PDF2D_2)
JPEG2000 (writer PDF2D_2)

Bookmark: Scale
AttributeManager_7
    ATTR_TABLE:
      SET_TO arrow1x = @Evaluate($(Coord_LR_x)-(@Value(_indices{1}.x)-@Value(_indices{0}.x))*0.35)
      SET_TO arrow1y = $(Coord_LR_y)
      SET_TO arrow2x = @Evaluate($(Coord_LR_x)-(@Value(_indices{1}.x)-@Value(_indices{0}.x))*0.35)
      SET_TO arrow2y = @Evaluate(@sum($(Coord_LR_y),@mult((@Value(_indices{1}.x)-@Value(_indices{0}.x))*0.015,@cos(@mult(@pi(),0.555555555,$(Coord_LR_y))))))
      SET_TO arrow3x = @Evaluate($(Coord_LR_x)-(@Value(_indices{1}.x)-@Value(_indices{0}.x))*0.55)
      SET_TO arrow3y = @Evaluate(@sum($(Coord_LR_y),@mult((@Value(_indices{1}.x)-@Value(_indices{0}.x))*0.015,@cos(@mult(@pi(),0.555555555,$(Coord_LR_y))))))
      SET_TO arrow4x = @Evaluate($(Coord_LR_x)-(@Value(_indices{1}.x)-@Value(_indices{0}.x))*0.55)
      SET_TO arrow4y = $(Coord_LR_y)
    -> Cloner_3
Cloner_3
    COPIES = 5
    COPYATT = _copynum
    COPY -> AttributeManager_8
AttributeManager_8
    ATTR_TABLE:
      SET_TO x = FME_CONDITIONAL:DEFAULT_VALUE'_FME_NO_OP_'BOOL_OP;OR;COMPOSITE_TEST;1;TEST @Value(_copynum) = 0'@Value(arrow1x)'BOOL_OP;OR;COMPOSITE_TEST;1;TEST @Value(_copynum) = 1'@Value(arrow2x)'BOOL_OP;OR;COMPOSITE_TEST;1;TEST @Value(_copynum) = 2'@Value(arrow3x)'BOOL_OP;OR;COMPOSITE_TEST;1;TEST @Value(_copynum) = 3'@Value(arrow4x)'BOOL_OP;OR;COMPOSITE_TEST;1;TEST @Value(_copynum) = 4'@Value(arrow1x)'FME_NUM_CONDITIONS6___
      SET_TO y = FME_CONDITIONAL:DEFAULT_VALUE'_FME_NO_OP_'BOOL_OP;OR;COMPOSITE_TEST;1;TEST @Value(_copynum) = 0'@Value(arrow1y)'BOOL_OP;OR;COMPOSITE_TEST;1;TEST @Value(_copynum) = 1'@Value(arrow2y)'BOOL_OP;OR;COMPOSITE_TEST;1;TEST @Value(_copynum) = 2'@Value(arrow3y)'BOOL_OP;OR;COMPOSITE_TEST;1;TEST @Value(_copynum) = 3'@Value(arrow4y)'BOOL_OP;OR;COMPOSITE_TEST;1;TEST @Value(_copynum) = 4'@Value(arrow1y)'FME_NUM_CONDITIONS6___
    -> AttributeManager_9
AttributeManager_9
    ATTR_TABLE:
      REMOVE _indices{}.x
      REMOVE _indices{}.y
      REMOVE _indices{}.z
      REMOVE arrow1x
      REMOVE arrow1y
      REMOVE arrow2x
      REMOVE arrow2y
      REMOVE arrow3x
      REMOVE arrow3y
      REMOVE arrow4x
      REMOVE arrow4y
    -> GeometryRemover_3
GeometryRemover_3
    -> VertexCreator_4
VertexCreator_4
    MEASURE_TYPE = Continuous
    MISSING_VAL_MODE = Compute
    MODE_NAME = Add Point
    XVAL = @Value(x)
    YVAL = @Value(y)
    -> LineBuilder_3
AttributeManager_4
    ATTR_TABLE:
      SET_TO arrow1x = @Evaluate($(Coord_LR_x)-(@Value(_indices{1}.x)-@Value(_indices{0}.x))*0.147)
      SET_TO arrow1y = $(Coord_LR_y)
      SET_TO arrow2x = @Evaluate($(Coord_LR_x)-(@Value(_indices{1}.x)-@Value(_indices{0}.x))*0.147)
      SET_TO arrow2y = @Evaluate(@sum($(Coord_LR_y),@mult((@Value(_indices{1}.x)-@Value(_indices{0}.x))*0.015,@cos(@mult(@pi(),0.555555555,$(Coord_LR_y))))))
      SET_TO arrow3x = @Evaluate($(Coord_LR_x)-(@Value(_indices{1}.x)-@Value(_indices{0}.x))*0.347)
      SET_TO arrow3y = @Evaluate(@sum($(Coord_LR_y),@mult((@Value(_indices{1}.x)-@Value(_indices{0}.x))*0.015,@cos(@mult(@pi(),0.555555555,$(Coord_LR_y))))))
      SET_TO arrow4x = @Evaluate($(Coord_LR_x)-(@Value(_indices{1}.x)-@Value(_indices{0}.x))*0.347)
      SET_TO arrow4y = $(Coord_LR_y)
    -> Cloner_2
Cloner_2
    COPIES = 5
    COPYATT = _copynum
    COPY -> AttributeManager_5
AttributeManager_5
    ATTR_TABLE:
      SET_TO x = FME_CONDITIONAL:DEFAULT_VALUE'_FME_NO_OP_'BOOL_OP;OR;COMPOSITE_TEST;1;TEST @Value(_copynum) = 0'@Value(arrow1x)'BOOL_OP;OR;COMPOSITE_TEST;1;TEST @Value(_copynum) = 1'@Value(arrow2x)'BOOL_OP;OR;COMPOSITE_TEST;1;TEST @Value(_copynum) = 2'@Value(arrow3x)'BOOL_OP;OR;COMPOSITE_TEST;1;TEST @Value(_copynum) = 3'@Value(arrow4x)'BOOL_OP;OR;COMPOSITE_TEST;1;TEST @Value(_copynum) = 4'@Value(arrow1x)'FME_NUM_CONDITIONS6___
      SET_TO y = FME_CONDITIONAL:DEFAULT_VALUE'_FME_NO_OP_'BOOL_OP;OR;COMPOSITE_TEST;1;TEST @Value(_copynum) = 0'@Value(arrow1y)'BOOL_OP;OR;COMPOSITE_TEST;1;TEST @Value(_copynum) = 1'@Value(arrow2y)'BOOL_OP;OR;COMPOSITE_TEST;1;TEST @Value(_copynum) = 2'@Value(arrow3y)'BOOL_OP;OR;COMPOSITE_TEST;1;TEST @Value(_copynum) = 3'@Value(arrow4y)'BOOL_OP;OR;COMPOSITE_TEST;1;TEST @Value(_copynum) = 4'@Value(arrow1y)'FME_NUM_CONDITIONS6___
    -> AttributeManager_6
AttributeManager_6
    ATTR_TABLE:
      REMOVE _indices{}.x
      REMOVE _indices{}.y
      REMOVE _indices{}.z
      REMOVE arrow1x
      REMOVE arrow1y
      REMOVE arrow2x
      REMOVE arrow2y
      REMOVE arrow3x
      REMOVE arrow3y
      REMOVE arrow4x
      REMOVE arrow4y
    -> GeometryRemover_2
GeometryRemover_2
    -> VertexCreator_2
VertexCreator_2
    MEASURE_TYPE = Continuous
    MISSING_VAL_MODE = Compute
    MODE_NAME = Add Point
    XVAL = @Value(x)
    YVAL = @Value(y)
    -> LineBuilder_2

Bookmark: Number on scale
Cloner_4
    COPIES = 3
    COPYATT = _copynum
    COPY -> AttributeManager_11
AttributeManager_11
    ATTR_TABLE:
      SET_TO label_pos_x = FME_CONDITIONAL:DEFAULT_VALUE'_FME_NO_OP_'BOOL_OP;OR;COMPOSITE_TEST;1;TEST @Value(_copynum) = 0'@Evaluate(@Value(arrow1x)-@Value(dist))'BOOL_OP;OR;COMPOSITE_TEST;1;TEST @Value(_copynum) = 1'@Evaluate(@Value(arrow1x)-(@Value(dist)/2))'BOOL_OP;OR;COMPOSITE_TEST;1;TEST @Value(_copynum) = 2'@Value(arrow1x)'FME_NUM_CONDITIONS4___
      SET_TO label_pos_y = @Value(arrow1y)
      SET_TO scale_to_print = @Evaluate(@round(@mult(@abs(@Value(arrow1x)-@Value(label_pos_x)),111),1))
    -> AttributeManager_12
AttributeManager_12
    ATTR_TABLE:
      REMOVE arrow1x
      REMOVE arrow1y
      REMOVE arrow2x
      REMOVE arrow2y
      SET_TO label_to_print = @Value(scale_to_print)
      REMOVE scale_to_print
    -> GeometryRemover_4
GeometryRemover_4
    -> VertexCreator_5
VertexCreator_5
    MEASURE_TYPE = Continuous
    MISSING_VAL_MODE = Compute
    MODE_NAME = Add Point
    XVAL = @Value(label_pos_x)
    YVAL = @Value(label_pos_y)
    -> LabelPointReplacer
LabelPointReplacer
    ALWAYSROTATE = yes
    HEIGHT = @Value(dist)*0.08
    LABATTR = @Value(label_to_print) km
    LabelPoint -> AttributeCreator_5

Bookmark: Arrow
AttributeManager
    ATTR_TABLE:
      SET_TO arrow1x = @Evaluate($(Coord_LR_x))
      SET_TO arrow1y = $(Coord_LR_y)
      SET_TO arrow2x = @Evaluate($(Coord_LR_x)-@mult(@Value(_indices{1}.x)-@Value(_indices{0}.x),0.05))
      SET_TO arrow2y = @Evaluate(@sum($(Coord_LR_y),@mult((@Value(_indices{1}.x)-@Value(_indices{0}.x))*0.05,@cos(@mult(@pi(),0.555555555,$(Coord_LR_y))))))
      SET_TO arrow3x = @Evaluate($(Coord_LR_x)-(@Value(_indices{1}.x)-@Value(_indices{0}.x))*0.1)
      SET_TO arrow3y = $(Coord_LR_y)
      SET_TO arrow4x = @Evaluate($(Coord_LR_x)-(@Value(_indices{1}.x)-@Value(_indices{0}.x))*0.05)
      SET_TO arrow4y = @Evaluate(@sum($(Coord_LR_y),@mult((@Value(_indices{1}.x)-@Value(_indices{0}.x))*0.15,@cos(@mult(@pi(),0.555555555,$(Coord_LR_y))))))
    -> Cloner
Cloner
    COPIES = 5
    COPYATT = _copynum
    COPY -> AttributeManager_2
AttributeManager_2
    ATTR_TABLE:
      SET_TO x = FME_CONDITIONAL:DEFAULT_VALUE'_FME_NO_OP_'BOOL_OP;OR;COMPOSITE_TEST;1;TEST @Value(_copynum) = 0'@Value(arrow1x)'BOOL_OP;OR;COMPOSITE_TEST;1;TEST @Value(_copynum) = 1'@Value(arrow2x)'BOOL_OP;OR;COMPOSITE_TEST;1;TEST @Value(_copynum) = 2'@Value(arrow3x)'BOOL_OP;OR;COMPOSITE_TEST;1;TEST @Value(_copynum) = 3'@Value(arrow4x)'BOOL_OP;OR;COMPOSITE_TEST;1;TEST @Value(_copynum) = 4'@Value(arrow1x)'FME_NUM_CONDITIONS6___
      SET_TO y = FME_CONDITIONAL:DEFAULT_VALUE'_FME_NO_OP_'BOOL_OP;OR;COMPOSITE_TEST;1;TEST @Value(_copynum) = 0'@Value(arrow1y)'BOOL_OP;OR;COMPOSITE_TEST;1;TEST @Value(_copynum) = 1'@Value(arrow2y)'BOOL_OP;OR;COMPOSITE_TEST;1;TEST @Value(_copynum) = 2'@Value(arrow3y)'BOOL_OP;OR;COMPOSITE_TEST;1;TEST @Value(_copynum) = 3'@Value(arrow4y)'BOOL_OP;OR;COMPOSITE_TEST;1;TEST @Value(_copynum) = 4'@Value(arrow1y)'FME_NUM_CONDITIONS6___
    -> AttributeManager_3
AttributeManager_3
    ATTR_TABLE:
      REMOVE _indices{}.x
      REMOVE _indices{}.y
      REMOVE _indices{}.z
      REMOVE arrow1x
      REMOVE arrow1y
      REMOVE arrow2x
      REMOVE arrow2y
      REMOVE arrow3x
      REMOVE arrow3y
      REMOVE arrow4x
      REMOVE arrow4y
    -> GeometryRemover
GeometryRemover
    -> VertexCreator_3
VertexCreator_3
    MEASURE_TYPE = Continuous
    MISSING_VAL_MODE = Compute
    MODE_NAME = Add Point
    XVAL = @Value(x)
    YVAL = @Value(y)
    -> LineBuilder
