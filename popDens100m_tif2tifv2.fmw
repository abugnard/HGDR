FME workspace popDens100m_tif2tifv2.fmw

Parameters:
- URL_DL_1 = https://data.worldpop.org/GIS/Population/Global_2000_2020/2020/HTI/hti_ppp_2020.tif   # URL for OSM DL
- URL_DL_2 = https://data.worldpop.org/GIS/Population/Global_2000_2020/2020/DOM/dom_ppp_2020.tif   # URL for OSM DL
- URL_DL_3 = https://data.worldpop.org/GIS/Population/Global_2000_2020/2020/HTI/hti_ppp_2020.tif   # URL for OSM DL
- URL_DL_4 = https://data.worldpop.org/GIS/Population/Global_2000_2020/2020/HTI/hti_ppp_2020.tif   # URL for OSM DL
- URL_DL_5 = https://data.worldpop.org/GIS/Population/Global_2000_2020/2020/HTI/hti_ppp_2020.tif   # URL for OSM DL
- URL_DL_6 = https://data.worldpop.org/GIS/Population/Global_2000_2020/2020/HTI/hti_ppp_2020.tif   # URL for OSM DL
- URL_DL_7 = https://data.worldpop.org/GIS/Population/Global_2000_2020/2020/HTI/hti_ppp_2020.tif   # URL for OSM DL
- URL_DL_8 = https://data.worldpop.org/GIS/Population/Global_2000_2020/2020/HTI/hti_ppp_2020.tif   # URL for OSM DL
- ISO_code = CHE   # Choose ISO code of country
- GEOM = -71.96266958667862 19.304860062881342 -71.48604373677655 19.781485912783392   # BoundingBox
- DestDataset_GEOTIFF = $(FME_MF_DIR)output_$(ISO_code)\03_Population_density   # Destination GeoTIFF Folder
- year_last = 2020   # Year of the file

Writers:
- GEOTIFF_1: GEOTIFF to $(DestDataset_GEOTIFF)

Creator_2
    COORDS = $(GEOM)
    COORDSYS = LL-WGS84
    GEOMTYPE = 2D Min/Max Box
    NUM = 1
    CREATED -> FeatureReader_2 [INITIATOR]
    CREATED -> Tester
    CREATED -> Tester_2
    CREATED -> Tester_3
    CREATED -> Tester_4
    CREATED -> Tester_5
    CREATED -> Tester_6
    CREATED -> Tester_7
    CREATED -> Clipper [CLIPPER]
FeatureReader_2
    ATTR_ACCUM_MODE = Only Use Result
    COMBINE_GEOM = Use Result
    DATASET = $(URL_DL_1)
    FEATURETYPES = GEOTIFF
    FORMAT = GEOTIFF
    GEOTIFF_APPLY_GCPS = NO
    GEOTIFF_FEATURE_TYPE_NAME = FORMAT_NAME
    GEOTIFF_IGNORE_RASTER_TYPE_KEY = No
    GEOTIFF_PREFER_FILE_CS_UNITS = Yes
    GEOTIFF_READER_META_ATTRIBUTES = fme_dataset fme_basename
    GEOTIFF_READ_OFFSETS_IN_CS_UNITS = No
    GEOTIFF_USE_SEARCH_ENVELOPE = NO
    INTERACT = Initiator Intersects Result
    OUTPUT_FEATURES_DISPLAY = Schema and Data Features
    <OTHER> -> RasterMosaicker
Tester_7
    BOOL_OP = COMPOSITE
    COMPOSITE_TEST = 1 AND 2 AND 3 AND 4 AND 5 AND 6 AND 7 AND 8 AND 9 AND 10 AND 11 AND 12 AND 13 AND 14 AND 15 AND 16 AND 17 AND 18 AND 19 AND 20 AND 21 AND 22 AND 23 AND 24 AND 25 AND 26 AND 27 AND 28
    TEST_CLAUSE:
      TEST $(URL_DL_1) != $(URL_DL_2)
      TEST $(URL_DL_1) != $(URL_DL_3)
      TEST $(URL_DL_1) != $(URL_DL_4)
      TEST $(URL_DL_1) != $(URL_DL_5)
      TEST $(URL_DL_1) != $(URL_DL_6)
      TEST $(URL_DL_1) != $(URL_DL_7)
      TEST $(URL_DL_1) != $(URL_DL_8)
      TEST $(URL_DL_2) != $(URL_DL_3)
      TEST $(URL_DL_2) != $(URL_DL_4)
      TEST $(URL_DL_2) != $(URL_DL_5)
      TEST $(URL_DL_2) != $(URL_DL_6)
      TEST $(URL_DL_2) != $(URL_DL_7)
      TEST $(URL_DL_2) != $(URL_DL_8)
      TEST $(URL_DL_3) != $(URL_DL_4)
      TEST $(URL_DL_3) != $(URL_DL_5)
      TEST $(URL_DL_3) != $(URL_DL_6)
      TEST $(URL_DL_3) != $(URL_DL_7)
      TEST $(URL_DL_3) != $(URL_DL_8)
      TEST $(URL_DL_4) != $(URL_DL_5)
      TEST $(URL_DL_4) != $(URL_DL_6)
      TEST $(URL_DL_4) != $(URL_DL_7)
      TEST $(URL_DL_4) != $(URL_DL_8)
      TEST $(URL_DL_5) != $(URL_DL_6)
      TEST $(URL_DL_5) != $(URL_DL_7)
      TEST $(URL_DL_5) != $(URL_DL_8)
      TEST $(URL_DL_6) != $(URL_DL_7)
      TEST $(URL_DL_6) != $(URL_DL_8)
      TEST $(URL_DL_7) != $(URL_DL_8)
    TEST_MODE = TEST
    PASSED -> FeatureReader_9 [INITIATOR]
FeatureReader_9
    ATTR_ACCUM_MODE = Only Use Result
    COMBINE_GEOM = Use Result
    DATASET = $(URL_DL_8)
    FEATURETYPES = GEOTIFF
    FORMAT = GEOTIFF
    GEOTIFF_APPLY_GCPS = NO
    GEOTIFF_FEATURE_TYPE_NAME = FORMAT_NAME
    GEOTIFF_IGNORE_RASTER_TYPE_KEY = No
    GEOTIFF_PREFER_FILE_CS_UNITS = Yes
    GEOTIFF_READER_META_ATTRIBUTES = fme_dataset fme_basename
    GEOTIFF_READ_OFFSETS_IN_CS_UNITS = No
    GEOTIFF_USE_SEARCH_ENVELOPE = NO
    INTERACT = Initiator Intersects Result
    OUTPUT_FEATURES_DISPLAY = Schema and Data Features
    <OTHER> -> RasterMosaicker
Tester_6
    BOOL_OP = COMPOSITE
    COMPOSITE_TEST = 1 AND 2 AND 3 AND 4 AND 5 AND 6 AND 7 AND 8 AND 9 AND 10 AND 11 AND 12 AND 13 AND 14 AND 15 AND 16 AND 17 AND 18 AND 19 AND 20 AND 21
    TEST_CLAUSE:
      TEST $(URL_DL_1) != $(URL_DL_2)
      TEST $(URL_DL_1) != $(URL_DL_3)
      TEST $(URL_DL_1) != $(URL_DL_4)
      TEST $(URL_DL_1) != $(URL_DL_5)
      TEST $(URL_DL_1) != $(URL_DL_6)
      TEST $(URL_DL_1) != $(URL_DL_7)
      TEST $(URL_DL_2) != $(URL_DL_3)
      TEST $(URL_DL_2) != $(URL_DL_4)
      TEST $(URL_DL_2) != $(URL_DL_5)
      TEST $(URL_DL_2) != $(URL_DL_6)
      TEST $(URL_DL_2) != $(URL_DL_7)
      TEST $(URL_DL_3) != $(URL_DL_4)
      TEST $(URL_DL_3) != $(URL_DL_5)
      TEST $(URL_DL_3) != $(URL_DL_6)
      TEST $(URL_DL_3) != $(URL_DL_7)
      TEST $(URL_DL_4) != $(URL_DL_5)
      TEST $(URL_DL_4) != $(URL_DL_6)
      TEST $(URL_DL_4) != $(URL_DL_7)
      TEST $(URL_DL_5) != $(URL_DL_6)
      TEST $(URL_DL_5) != $(URL_DL_7)
      TEST $(URL_DL_6) != $(URL_DL_7)
    TEST_MODE = TEST
    PASSED -> FeatureReader_8 [INITIATOR]
FeatureReader_8
    ATTR_ACCUM_MODE = Only Use Result
    COMBINE_GEOM = Use Result
    DATASET = $(URL_DL_7)
    FEATURETYPES = GEOTIFF
    FORMAT = GEOTIFF
    GEOTIFF_APPLY_GCPS = NO
    GEOTIFF_FEATURE_TYPE_NAME = FORMAT_NAME
    GEOTIFF_IGNORE_RASTER_TYPE_KEY = No
    GEOTIFF_PREFER_FILE_CS_UNITS = Yes
    GEOTIFF_READER_META_ATTRIBUTES = fme_dataset fme_basename
    GEOTIFF_READ_OFFSETS_IN_CS_UNITS = No
    GEOTIFF_USE_SEARCH_ENVELOPE = NO
    INTERACT = Initiator Intersects Result
    OUTPUT_FEATURES_DISPLAY = Schema and Data Features
    <OTHER> -> RasterMosaicker
Tester_5
    BOOL_OP = COMPOSITE
    COMPOSITE_TEST = 1 AND 2 AND 3 AND 4 AND 5 AND 6 AND 7 AND 8 AND 9 AND 10 AND 11 AND 12 AND 13 AND 14 AND 15
    TEST_CLAUSE:
      TEST $(URL_DL_1) != $(URL_DL_2)
      TEST $(URL_DL_1) != $(URL_DL_3)
      TEST $(URL_DL_1) != $(URL_DL_4)
      TEST $(URL_DL_1) != $(URL_DL_5)
      TEST $(URL_DL_1) != $(URL_DL_6)
      TEST $(URL_DL_2) != $(URL_DL_3)
      TEST $(URL_DL_2) != $(URL_DL_4)
      TEST $(URL_DL_2) != $(URL_DL_5)
      TEST $(URL_DL_2) != $(URL_DL_6)
      TEST $(URL_DL_3) != $(URL_DL_4)
      TEST $(URL_DL_3) != $(URL_DL_5)
      TEST $(URL_DL_3) != $(URL_DL_6)
      TEST $(URL_DL_4) != $(URL_DL_5)
      TEST $(URL_DL_4) != $(URL_DL_6)
      TEST $(URL_DL_5) != $(URL_DL_6)
    TEST_MODE = TEST
    PASSED -> FeatureReader_7 [INITIATOR]
FeatureReader_7
    ATTR_ACCUM_MODE = Only Use Result
    COMBINE_GEOM = Use Result
    DATASET = $(URL_DL_6)
    FEATURETYPES = GEOTIFF
    FORMAT = GEOTIFF
    GEOTIFF_APPLY_GCPS = NO
    GEOTIFF_FEATURE_TYPE_NAME = FORMAT_NAME
    GEOTIFF_IGNORE_RASTER_TYPE_KEY = No
    GEOTIFF_PREFER_FILE_CS_UNITS = Yes
    GEOTIFF_READER_META_ATTRIBUTES = fme_dataset fme_basename
    GEOTIFF_READ_OFFSETS_IN_CS_UNITS = No
    GEOTIFF_USE_SEARCH_ENVELOPE = NO
    INTERACT = Initiator Intersects Result
    OUTPUT_FEATURES_DISPLAY = Schema and Data Features
    <OTHER> -> RasterMosaicker
Tester_4
    BOOL_OP = AND
    COMPOSITE_TEST = 1 AND 2 AND 3 AND 4 AND 5 AND 6 AND 7 AND 8 AND 9 AND 10
    TEST_CLAUSE:
      TEST $(URL_DL_1) != $(URL_DL_2)
      TEST $(URL_DL_1) != $(URL_DL_3)
      TEST $(URL_DL_1) != $(URL_DL_4)
      TEST $(URL_DL_1) != $(URL_DL_5)
      TEST $(URL_DL_2) != $(URL_DL_3)
      TEST $(URL_DL_2) != $(URL_DL_4)
      TEST $(URL_DL_2) != $(URL_DL_5)
      TEST $(URL_DL_3) != $(URL_DL_4)
      TEST $(URL_DL_3) != $(URL_DL_5)
      TEST $(URL_DL_4) != $(URL_DL_5)
    TEST_MODE = TEST
    PASSED -> FeatureReader_6 [INITIATOR]
FeatureReader_6
    ATTR_ACCUM_MODE = Only Use Result
    COMBINE_GEOM = Use Result
    DATASET = $(URL_DL_5)
    FEATURETYPES = GEOTIFF
    FORMAT = GEOTIFF
    GEOTIFF_APPLY_GCPS = NO
    GEOTIFF_FEATURE_TYPE_NAME = FORMAT_NAME
    GEOTIFF_IGNORE_RASTER_TYPE_KEY = No
    GEOTIFF_PREFER_FILE_CS_UNITS = Yes
    GEOTIFF_READER_META_ATTRIBUTES = fme_dataset fme_basename
    GEOTIFF_READ_OFFSETS_IN_CS_UNITS = No
    GEOTIFF_USE_SEARCH_ENVELOPE = NO
    INTERACT = Initiator Intersects Result
    OUTPUT_FEATURES_DISPLAY = Schema and Data Features
    <OTHER> -> RasterMosaicker
Tester_3
    BOOL_OP = AND
    COMPOSITE_TEST = 1 AND 2 AND 3 AND 4 AND 5 AND 6
    TEST_CLAUSE:
      TEST $(URL_DL_1) != $(URL_DL_2)
      TEST $(URL_DL_1) != $(URL_DL_3)
      TEST $(URL_DL_1) != $(URL_DL_4)
      TEST $(URL_DL_2) != $(URL_DL_3)
      TEST $(URL_DL_2) != $(URL_DL_4)
      TEST $(URL_DL_3) != $(URL_DL_4)
    TEST_MODE = TEST
    PASSED -> FeatureReader_5 [INITIATOR]
FeatureReader_5
    ATTR_ACCUM_MODE = Only Use Result
    COMBINE_GEOM = Use Result
    DATASET = $(URL_DL_4)
    FEATURETYPES = GEOTIFF
    FORMAT = GEOTIFF
    GEOTIFF_APPLY_GCPS = NO
    GEOTIFF_FEATURE_TYPE_NAME = FORMAT_NAME
    GEOTIFF_IGNORE_RASTER_TYPE_KEY = No
    GEOTIFF_PREFER_FILE_CS_UNITS = Yes
    GEOTIFF_READER_META_ATTRIBUTES = fme_dataset fme_basename
    GEOTIFF_READ_OFFSETS_IN_CS_UNITS = No
    GEOTIFF_USE_SEARCH_ENVELOPE = NO
    INTERACT = Initiator Intersects Result
    OUTPUT_FEATURES_DISPLAY = Schema and Data Features
    <OTHER> -> RasterMosaicker
Tester_2
    BOOL_OP = AND
    COMPOSITE_TEST = 1 AND 2 AND 3
    TEST_CLAUSE:
      TEST $(URL_DL_1) != $(URL_DL_2)
      TEST $(URL_DL_2) != $(URL_DL_3)
      TEST $(URL_DL_1) != $(URL_DL_3)
    TEST_MODE = TEST
    PASSED -> FeatureReader_4 [INITIATOR]
FeatureReader_4
    ATTR_ACCUM_MODE = Only Use Result
    COMBINE_GEOM = Use Result
    DATASET = $(URL_DL_3)
    FEATURETYPES = GEOTIFF
    FORMAT = GEOTIFF
    GEOTIFF_APPLY_GCPS = NO
    GEOTIFF_FEATURE_TYPE_NAME = FORMAT_NAME
    GEOTIFF_IGNORE_RASTER_TYPE_KEY = No
    GEOTIFF_PREFER_FILE_CS_UNITS = Yes
    GEOTIFF_READER_META_ATTRIBUTES = fme_dataset fme_basename
    GEOTIFF_READ_OFFSETS_IN_CS_UNITS = No
    GEOTIFF_USE_SEARCH_ENVELOPE = NO
    INTERACT = Initiator Intersects Result
    OUTPUT_FEATURES_DISPLAY = Schema and Data Features
    <OTHER> -> RasterMosaicker
Tester
    BOOL_OP = OR
    COMPOSITE_TEST = 1
    TEST_CLAUSE = TEST $(URL_DL_1) != $(URL_DL_2)
    TEST_MODE = TEST
    PASSED -> FeatureReader_3 [INITIATOR]
FeatureReader_3
    ATTR_ACCUM_MODE = Only Use Result
    COMBINE_GEOM = Use Result
    DATASET = $(URL_DL_2)
    FEATURETYPES = GEOTIFF
    FORMAT = GEOTIFF
    GEOTIFF_APPLY_GCPS = NO
    GEOTIFF_FEATURE_TYPE_NAME = FORMAT_NAME
    GEOTIFF_IGNORE_RASTER_TYPE_KEY = No
    GEOTIFF_PREFER_FILE_CS_UNITS = Yes
    GEOTIFF_READER_META_ATTRIBUTES = fme_dataset fme_basename
    GEOTIFF_READ_OFFSETS_IN_CS_UNITS = No
    GEOTIFF_USE_SEARCH_ENVELOPE = NO
    INTERACT = Initiator Intersects Result
    OUTPUT_FEATURES_DISPLAY = Schema and Data Features
    <OTHER> -> RasterMosaicker
RasterMosaicker
    ACCUM_ATTRS_NAME = Use Attributes From One Feature
    INTERPOLATION_TYPE_NAME = Nearest Neighbor
    MERGE_PALETTES_NAME = Yes
    NODATA_OVERWRITE = No
    OVERLAPPING_VALUES = last
    SNAPPING_TYPE_NAME = Offset
    -> Clipper [CLIPPEE]
Clipper
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> RasterConvolver
RasterConvolver
    CENTER_PIXEL_NODATA_HANDLING = OutputNodata
    CONVOLUTION_FILTER = UserDefined
    EDGE_HANDLING = ExtendBorderValues
    KERNEL_DIVISOR = Sum of Kernel Weights
    KERNEL_OPERATION = Mean
    KERNEL_WEIGHTS = 1 1 1 1 1 1 1 1 1 1 1 1 1 1 1 1 1 1 1 1 1 1 1 1 1 1 1 1 1 1 1 1 1 1 1 1 1 4 6 4 1 1 1 1 1 1 1 4 16 24 16 4 1 1 1 1 1 1 6 24 36 24 6 1 1 1 1 1 1 4 16 24 16 4 1 1 1 1 1 1 1 4 6 4 1 1 1 1 1 1 1 1 1 1 1 1 1 1 1 1 1 1 1 1 1 1 1 1 1 1 1 1 1 1 1 1 1 1 1 1 1
    NEIGHBOR_PIXEL_NODATA_HANDLING = UseCenterPixel
    PRESERVE_BAND_INTERPRETATION = No
    -> popDens100m_2020 (writer GEOTIFF_1)
popDens100m_2020 (writer GEOTIFF_1)
    attributes: _clipped char(200)
