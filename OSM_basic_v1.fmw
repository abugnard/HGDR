FME workspace OSM_basic_v1.fmw

Parameters:
- FEATURETYPES = boundary highway   # Feature Types to Read
- DestDataset_SHAPEFILE = $(FME_MF_DIR)output_tuvalu\Line   # Destination Esri Shapefile Folder
- DestDataset_SHAPEFILE_5 = $(FME_MF_DIR)output_tuvalu\Polygone   # Destination Esri Shapefile Folder
- DestDataset_SHAPEFILE_4 = $(FME_MF_DIR)output_tuvalu\Point   # Destination Esri Shapefile Folder
- GEOM = <?xml version="1.0" encoding="US_ASCII" standalone="no" ?><geometry><polygon><line><coord x="179.193" y="-8.543"/><coord x="179.205" y="-8.543"/><coord x="179.205" y="-8.47"/><coord x="179.193" y="-8.47"/><coord x="179.193" y="-8.543"/></line></polygon></geometry>   # Geometry Object
- URL_DL_1 = https://download.geofabrik.de/australia-oceania/tuvalu-latest.osm.pbf   # URL for OSM DL
- URL_DL_2 = https://download.geofabrik.de/australia-oceania/samoa-latest.osm.pbf   # URL for OSM DL
- URL_DL_3 = https://download.geofabrik.de/australia-oceania/tonga-latest.osm.pbf   # URL for OSM DL
- URL_DL_4 = https://download.geofabrik.de/australia-oceania/tuvalu-latest.osm.pbf   # URL for OSM DL
- ISO_code = TU   # Enter the ISO 3166 code of the country of interest

Writers:
- SHAPEFILE_1: SHAPEFILE to $(DestDataset_SHAPEFILE)
- SHAPEFILE_2: SHAPEFILE to $(DestDataset_SHAPEFILE_5)
- SHAPEFILE_3: SHAPEFILE to $(DestDataset_SHAPEFILE_4)

Creator
    GEOMTYPE = Geometry Object
    NUM = 1
    CREATED -> FeatureReader [INITIATOR]
    CREATED -> Tester
    CREATED -> Tester_2
    CREATED -> Tester_3
Clipper
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> AttributeCreator
Note: Add date/time to the files
AttributeCreator
    ATTR_TABLE:
      SET_TO time = @DateTimeFormat(@DateTimeNow(),%Y%m%d%H)
      SET_TO feature_type = @Value(fme_feature_type)

      SET_TO local_name = @Value(name)
      SET_TO english_name = @Value(name:en)
      SET_TO boundary = @Value(boundary)
      SET_TO COI = $(ISO_code)
    -> GeometryFilter
GeometryFilter
    BREAK_AGG = No
    GEOM_PORT_NAMES = Collection Point Line Arc Area Ellipse Text Raster "Point Cloud" Surface Solid Null Instance
    POINT -> Point_v2 (writer SHAPEFILE_3)
    LINE -> Line_v2 (writer SHAPEFILE_1)
    AREA -> Polygone_v2 (writer SHAPEFILE_2)

Bookmark: Data Download
FeatureReader
    ATTR_ACCUM_MODE = Only Use Result
    COMBINE_GEOM = Use Result
    DATASET = $(URL_DL_1)
    FEATURETYPES = $(FEATURETYPES)
    FORMAT = OSMPBF
    INTERACT = <No Spatial Filter>
    OSMPBF_COMMUNITY_FEATURE_TYPES = MAPPED
    OSMPBF_HANDLE_MULTI = SELECT_FIRST
    OSMPBF_KEY_SCHEMA_MODE = EXCLUDE_KEYVAL_SCHEMAS
    OSMPBF_QUERY_FEATURE_TYPES_FOR_MERGE_FILTERS = Yes
    OSMPBF_READ_BOOLEANS_AS_YES_NO = YES
    OSMPBF_READ_NULLS = YES
    OSMPBF_USER_CONFIG = NO
    OSMPBF_USE_FAST_NODE_INDEX = Yes
    OSMPBF_USE_SEARCH_ENVELOPE = NO
    OUTPUT_FEATURES_DISPLAY = Schema and Data Features
    <OTHER> -> Clipper [CLIPPEE]
Tester
    BOOL_OP = OR
    COMPOSITE_TEST = 1
    TEST_CLAUSE = TEST $(URL_DL_1) != $(URL_DL_2)
    TEST_MODE = TEST
    PASSED -> FeatureReader_2 [INITIATOR]
FeatureReader_2
    ATTR_ACCUM_MODE = Only Use Result
    COMBINE_GEOM = Use Result
    DATASET = $(URL_DL_2)
    FEATURETYPES = $(FEATURETYPES)
    FORMAT = OSMPBF
    INTERACT = <No Spatial Filter>
    OSMPBF_COMMUNITY_FEATURE_TYPES = MAPPED
    OSMPBF_HANDLE_MULTI = SELECT_FIRST
    OSMPBF_KEY_SCHEMA_MODE = EXCLUDE_KEYVAL_SCHEMAS
    OSMPBF_QUERY_FEATURE_TYPES_FOR_MERGE_FILTERS = Yes
    OSMPBF_READ_BOOLEANS_AS_YES_NO = YES
    OSMPBF_READ_NULLS = YES
    OSMPBF_USER_CONFIG = NO
    OSMPBF_USE_FAST_NODE_INDEX = Yes
    OSMPBF_USE_SEARCH_ENVELOPE = NO
    OUTPUT_FEATURES_DISPLAY = Schema and Data Features
    <OTHER> -> Clipper [CLIPPEE]
Tester_2
    BOOL_OP = AND
    COMPOSITE_TEST = 1 AND 2 AND 3
    TEST_CLAUSE:
      TEST $(URL_DL_1) != $(URL_DL_2)
      TEST $(URL_DL_2) != $(URL_DL_3)
      TEST $(URL_DL_1) != $(URL_DL_3)
    TEST_MODE = TEST
    PASSED -> FeatureReader_3 [INITIATOR]
FeatureReader_3
    ATTR_ACCUM_MODE = Only Use Result
    COMBINE_GEOM = Use Result
    DATASET = $(URL_DL_3)
    FEATURETYPES = $(FEATURETYPES)
    FORMAT = OSMPBF
    INTERACT = <No Spatial Filter>
    OSMPBF_COMMUNITY_FEATURE_TYPES = MAPPED
    OSMPBF_HANDLE_MULTI = SELECT_FIRST
    OSMPBF_KEY_SCHEMA_MODE = EXCLUDE_KEYVAL_SCHEMAS
    OSMPBF_QUERY_FEATURE_TYPES_FOR_MERGE_FILTERS = Yes
    OSMPBF_READ_BOOLEANS_AS_YES_NO = YES
    OSMPBF_READ_NULLS = YES
    OSMPBF_USER_CONFIG = NO
    OSMPBF_USE_FAST_NODE_INDEX = Yes
    OSMPBF_USE_SEARCH_ENVELOPE = NO
    OUTPUT_FEATURES_DISPLAY = Schema and Data Features
    <OTHER> -> Clipper [CLIPPEE]
Tester_3
    BOOL_OP = AND
    COMPOSITE_TEST = 1 AND 2 AND 3 AND 4 AND 5 AND 6
    TEST_CLAUSE:
      TEST $(URL_DL_1) != $(URL_DL_2)
      TEST $(URL_DL_1) != $(URL_DL_3)
      TEST $(URL_DL_1) != $(URL_DL_4)
      TEST $(URL_DL_2) != $(URL_DL_3)
      TEST $(URL_DL_2) != $(URL_DL_4)
      TEST $(URL_DL_3) != $(URL_DL_4)
    TEST_MODE = TEST
    PASSED -> FeatureReader_4 [INITIATOR]
FeatureReader_4
    ATTR_ACCUM_MODE = Only Use Result
    COMBINE_GEOM = Use Result
    DATASET = $(URL_DL_4)
    FEATURETYPES = $(FEATURETYPES)
    FORMAT = OSMPBF
    INTERACT = <No Spatial Filter>
    OSMPBF_COMMUNITY_FEATURE_TYPES = MAPPED
    OSMPBF_HANDLE_MULTI = SELECT_FIRST
    OSMPBF_KEY_SCHEMA_MODE = EXCLUDE_KEYVAL_SCHEMAS
    OSMPBF_QUERY_FEATURE_TYPES_FOR_MERGE_FILTERS = Yes
    OSMPBF_READ_BOOLEANS_AS_YES_NO = YES
    OSMPBF_READ_NULLS = YES
    OSMPBF_USER_CONFIG = NO
    OSMPBF_USE_FAST_NODE_INDEX = Yes
    OSMPBF_USE_SEARCH_ENVELOPE = NO
    OUTPUT_FEATURES_DISPLAY = Schema and Data Features
    <OTHER> -> Clipper [CLIPPEE]

Bookmark: BoundingBox
Creator_2
    COORDSYS = LL-WGS84
    GEOM = $(GEOM)
    GEOMTYPE = Geometry Object
    NUM = 1
    CREATED -> CoordinateSystemSetter
CoordinateSystemSetter
    COORDSYS = LL-WGS84
    -> LengthCalculator
LengthCalculator
    DIM = 2
    LEN_ATTR = _length
    MULT = 1
    -> Bufferer
Bufferer
    ANGLE = 22.5
    CAP_STYLE = Arc
    CORNER_STYLE = Arc
    MODE = AREA
    OFFSET = "@Value(_length)*0.1 "
    OFFSET_UNITS = NONE
    PRECISION = APPROX
    BUFFERED -> Clipper [CLIPPER]

Bookmark: Writers
Point_v2 (writer SHAPEFILE_3)
    attributes: time char(200), feature_ty char(200), local_name char(200), english_na char(200), boundary char(200), COI char(200), _clipped char(200)
Line_v2 (writer SHAPEFILE_1)
    attributes: time char(200), feature_ty char(200), local_name char(200), english_na char(200), boundary char(200), COI char(200), _clipped char(200)
Polygone_v2 (writer SHAPEFILE_2)
    attributes: time char(200), feature_ty char(200), local_name char(200), english_na char(200), boundary char(200), COI char(200), _clipped char(200)
