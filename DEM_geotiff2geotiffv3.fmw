FME workspace DEM_geotiff2geotiffv3.fmw

Parameters:
- DestDataset_GEOTIFF =
- GEOM_maxLAT =
- GEOM_maxLON =
- GEOM_minLAT =
- GEOM_minLON =
- ISO_code =
- SERVER_MODE =

Writers:
- GEOTIFF_1: GEOTIFF to $(DestDataset_GEOTIFF)

Creator_2
    COORDSYS = LL-WGS84
    GEOMTYPE = Geometry Object
    NUM = 1
    CREATED -> AttributeManager_38
    CREATED -> AttributeManager_37
    CREATED -> AttributeManager_48
    CREATED -> AttributeManager_39
    CREATED -> AttributeManager_40
    CREATED -> AttributeManager_41
    CREATED -> AttributeManager_42
    CREATED -> AttributeManager_47
    CREATED -> AttributeManager_45
    CREATED -> AttributeManager_46
    CREATED -> AttributeManager_44
    CREATED -> AttributeManager_43
    CREATED -> AttributeManager_36
    CREATED -> AttributeManager_35
    CREATED -> AttributeManager_34
    CREATED -> AttributeManager_33
    CREATED -> AttributeManager_32
    CREATED -> AttributeManager_31
    CREATED -> AttributeManager_30
    CREATED -> AttributeManager_29
    CREATED -> AttributeManager_28
    CREATED -> AttributeManager_27
    CREATED -> AttributeManager_2
    CREATED -> AttributeManager
    CREATED -> AttributeManager_15
    CREATED -> AttributeManager_16
    CREATED -> AttributeManager_17
    CREATED -> AttributeManager_18
    CREATED -> AttributeManager_19
    CREATED -> AttributeManager_20
    CREATED -> AttributeManager_21
    CREATED -> AttributeManager_22
    CREATED -> AttributeManager_24
    CREATED -> AttributeManager_25
    CREATED -> AttributeManager_26
    CREATED -> AttributeManager_14
    CREATED -> AttributeManager_13
    CREATED -> AttributeManager_12
    CREATED -> AttributeManager_11
    CREATED -> AttributeManager_10
    CREATED -> AttributeManager_9
    CREATED -> AttributeManager_8
    CREATED -> AttributeManager_7
    CREATED -> AttributeManager_6
    CREATED -> AttributeManager_5
    CREATED -> AttributeManager_4
    CREATED -> AttributeManager_49
    CREATED -> AttributeManager_50
    CREATED -> AttributeManager_51
    CREATED -> AttributeManager_52
    CREATED -> AttributeManager_53
    CREATED -> AttributeManager_54
    CREATED -> AttributeManager_55
    CREATED -> AttributeManager_56
    CREATED -> AttributeManager_57
    CREATED -> AttributeManager_58
    CREATED -> AttributeManager_59
    CREATED -> AttributeManager_60
    CREATED -> AttributeManager_61
    CREATED -> AttributeManager_62
    CREATED -> AttributeManager_63
    CREATED -> AttributeManager_64
    CREATED -> AttributeManager_65
    CREATED -> AttributeManager_66
    CREATED -> AttributeManager_67
    CREATED -> AttributeManager_68
    CREATED -> AttributeManager_69
    CREATED -> AttributeManager_70
    CREATED -> AttributeManager_71
    CREATED -> AttributeManager_72
    CREATED -> AttributeManager_73
    CREATED -> AttributeManager_74
    CREATED -> AttributeManager_75
    CREATED -> AttributeManager_76
    CREATED -> AttributeManager_77
    CREATED -> AttributeManager_78
    CREATED -> AttributeManager_79
    CREATED -> AttributeManager_80
    CREATED -> AttributeManager_81
    CREATED -> AttributeManager_82
    CREATED -> AttributeManager_83
    CREATED -> AttributeManager_84
    CREATED -> AttributeManager_85
    CREATED -> AttributeManager_87
    CREATED -> AttributeManager_88
    CREATED -> AttributeManager_89
    CREATED -> AttributeManager_90
    CREATED -> AttributeManager_91
    CREATED -> AttributeManager_92
    CREATED -> AttributeManager_93
    CREATED -> AttributeManager_94
    CREATED -> AttributeManager_95
    CREATED -> AttributeManager_96
    CREATED -> AttributeManager_97
    CREATED -> AttributeManager_98
    CREATED -> AttributeManager_99
    CREATED -> AttributeManager_100
    CREATED -> AttributeManager_101
    CREATED -> AttributeManager_102
    CREATED -> AttributeManager_103
    CREATED -> AttributeManager_104
    CREATED -> AttributeManager_105
    CREATED -> AttributeManager_106
    CREATED -> AttributeManager_107
    CREATED -> AttributeManager_108
    CREATED -> AttributeManager_3
    CREATED -> AttributeManager_23
    CREATED -> AttributeManager_86
AttributeManager_3
    ATTR_TABLE = SET_TO dataset_loc = FME_CONDITIONAL:DEFAULT_VALUE'fme://fme-server/70n000e_20101117_gmted_dsc075.tif?id=FME_SHAREDRESOURCE_DATA%2Ffilesys%2FHGDE%2FDEM%2FN70%2F70n000e_20101117_gmted_dsc075.tif&module=fmeserver&webservice=FME%20Server&connection=geopol'BOOL_OP;OR;COMPOSITE_TEST;1;TEST $(SERVER_MODE) = NO'$(FME_MF_DIR_ENCODED)DEM\N70\70n000e_20101117_gmted_dsc075.tif'FME_NUM_CONDITIONS2___
    -> N70E0
N70E0: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [70,90]
      NUM_TEST $(GEOM_maxLON) RANGE [0,30]
      NUM_TEST $(GEOM_maxLAT) RANGE [70,90]
      NUM_TEST $(GEOM_minLON) RANGE [0,30]
      NUM_TEST $(GEOM_minLAT) RANGE [70,90]
      NUM_TEST $(GEOM_minLON) RANGE [0,30]
      NUM_TEST $(GEOM_minLAT) RANGE [70,90]
      NUM_TEST $(GEOM_maxLON) RANGE [0,30]",<pass>
    <pass> -> FeatureReader_38 [INITIATOR]
FeatureReader_38
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_4
    ATTR_TABLE = SET_TO dataset_loc = FME_CONDITIONAL:DEFAULT_VALUE'fme://fme-server/70n030e_20101117_gmted_dsc075.tif?id=FME_SHAREDRESOURCE_DATA%2Ffilesys%2FHGDE%2FDEM%2FN70%2F70n030e_20101117_gmted_dsc075.tif&module=fmeserver&webservice=FME%20Server&connection=geopol'BOOL_OP;OR;COMPOSITE_TEST;1;TEST $(SERVER_MODE) = NO'$(FME_MF_DIR_ENCODED)DEM\N70\70n030e_20101117_gmted_dsc075.tif'FME_NUM_CONDITIONS2___
    -> N70E30
N70E30: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [70,90]
      NUM_TEST $(GEOM_maxLON) RANGE [30,60]
      NUM_TEST $(GEOM_maxLAT) RANGE [70,90]
      NUM_TEST $(GEOM_minLON) RANGE [30,60]
      NUM_TEST $(GEOM_minLAT) RANGE [70,90]
      NUM_TEST $(GEOM_minLON) RANGE [30,60]
      NUM_TEST $(GEOM_minLAT) RANGE [70,90]
      NUM_TEST $(GEOM_maxLON) RANGE [30,60]",<pass>
    <pass> -> FeatureReader_37 [INITIATOR]
FeatureReader_37
    ATTR_ACCUM_MODE = Only Use Result
    COMBINE_GEOM = Use Result
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_5
    ATTR_TABLE = SET_TO dataset_loc = FME_CONDITIONAL:DEFAULT_VALUE'fme://fme-server/70n060e_20101117_gmted_dsc075.tif?id=FME_SHAREDRESOURCE_DATA%2Ffilesys%2FHGDE%2FDEM%2FN70%2F70n060e_20101117_gmted_dsc075.tif&module=fmeserver&webservice=FME%20Server&connection=geopol'BOOL_OP;OR;COMPOSITE_TEST;1;TEST $(SERVER_MODE) = NO'$(FME_MF_DIR_ENCODED)DEM\N70\70N060E_20101117_gmted_dsc075.tif'FME_NUM_CONDITIONS2___
    -> N70E60
N70E60: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [70,90]
      NUM_TEST $(GEOM_maxLON) RANGE [60,90]
      NUM_TEST $(GEOM_maxLAT) RANGE [70,90]
      NUM_TEST $(GEOM_minLON) RANGE [60,90]
      NUM_TEST $(GEOM_minLAT) RANGE [70,90]
      NUM_TEST $(GEOM_minLON) RANGE [60,90]
      NUM_TEST $(GEOM_minLAT) RANGE [70,90]
      NUM_TEST $(GEOM_maxLON) RANGE [60,90]",<pass>
    <pass> -> FeatureReader_40 [INITIATOR]
FeatureReader_40
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_6
    ATTR_TABLE = SET_TO dataset_loc = FME_CONDITIONAL:DEFAULT_VALUE'fme://fme-server/70n090e_20101117_gmted_dsc075.tif?id=FME_SHAREDRESOURCE_DATA%2Ffilesys%2FHGDE%2FDEM%2FN70%2F70n090e_20101117_gmted_dsc075.tif&module=fmeserver&webservice=FME%20Server&connection=geopol'BOOL_OP;OR;COMPOSITE_TEST;1;TEST $(SERVER_MODE) = NO'$(FME_MF_DIR_ENCODED)DEM\N70\70N090E_20101117_gmted_dsc075.tif'FME_NUM_CONDITIONS2___
    -> N70E90
N70E90: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [70,90]
      NUM_TEST $(GEOM_maxLON) RANGE [90,120]
      NUM_TEST $(GEOM_maxLAT) RANGE [70,90]
      NUM_TEST $(GEOM_minLON) RANGE [90,120]
      NUM_TEST $(GEOM_minLAT) RANGE [70,90]
      NUM_TEST $(GEOM_minLON) RANGE [90,120]
      NUM_TEST $(GEOM_minLAT) RANGE [70,90]
      NUM_TEST $(GEOM_maxLON) RANGE [90,120]",<pass>
    <pass> -> FeatureReader_41 [INITIATOR]
FeatureReader_41
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_7
    ATTR_TABLE = SET_TO dataset_loc = FME_CONDITIONAL:DEFAULT_VALUE'fme://fme-server/70n120e_20101117_gmted_dsc075.tif?id=FME_SHAREDRESOURCE_DATA%2Ffilesys%2FHGDE%2FDEM%2FN70%2F70n120e_20101117_gmted_dsc075.tif&module=fmeserver&webservice=FME%20Server&connection=geopol'BOOL_OP;OR;COMPOSITE_TEST;1;TEST $(SERVER_MODE) = NO'$(FME_MF_DIR_ENCODED)DEM\N70\70n120e_20101117_gmted_dsc075.tif'FME_NUM_CONDITIONS2___
    -> N70E120
N70E120: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [70,90]
      NUM_TEST $(GEOM_maxLON) RANGE [120,150]
      NUM_TEST $(GEOM_maxLAT) RANGE [70,90]
      NUM_TEST $(GEOM_minLON) RANGE [120,150]
      NUM_TEST $(GEOM_minLAT) RANGE [70,90]
      NUM_TEST $(GEOM_minLON) RANGE [120,150]
      NUM_TEST $(GEOM_minLAT) RANGE [70,90]
      NUM_TEST $(GEOM_maxLON) RANGE [120,150]",<pass>
    <pass> -> FeatureReader_42 [INITIATOR]
FeatureReader_42
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_8
    ATTR_TABLE = SET_TO dataset_loc = FME_CONDITIONAL:DEFAULT_VALUE'fme://fme-server/70n150e_20101117_gmted_dsc075.tif?id=FME_SHAREDRESOURCE_DATA%2Ffilesys%2FHGDE%2FDEM%2FN70%2F70n150e_20101117_gmted_dsc075.tif&module=fmeserver&webservice=FME%20Server&connection=geopol'BOOL_OP;OR;COMPOSITE_TEST;1;TEST $(SERVER_MODE) = NO'$(FME_MF_DIR_ENCODED)DEM\N70\70n150e_20101117_gmted_dsc075.tif'FME_NUM_CONDITIONS2___
    -> N70E150
N70E150: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [70,90]
      NUM_TEST $(GEOM_maxLON) RANGE [150,180]
      NUM_TEST $(GEOM_maxLAT) RANGE [70,90]
      NUM_TEST $(GEOM_minLON) RANGE [150,180]
      NUM_TEST $(GEOM_minLAT) RANGE [70,90]
      NUM_TEST $(GEOM_minLON) RANGE [150,180]
      NUM_TEST $(GEOM_minLAT) RANGE [70,90]
      NUM_TEST $(GEOM_maxLON) RANGE [150,180]",<pass>
    <pass> -> FeatureReader_43 [INITIATOR]
FeatureReader_43
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_9
    ATTR_TABLE = SET_TO dataset_loc = FME_CONDITIONAL:DEFAULT_VALUE'fme://fme-server/70n180w_20101117_gmted_dsc075.tif?id=FME_SHAREDRESOURCE_DATA%2Ffilesys%2FHGDE%2FDEM%2FN70%2F70n180w_20101117_gmted_dsc075.tif&module=fmeserver&webservice=FME%20Server&connection=geopol'BOOL_OP;OR;COMPOSITE_TEST;1;TEST $(SERVER_MODE) = NO'$(FME_MF_DIR_ENCODED)DEM\N70\70n180w_20101117_gmted_dsc075.tif'FME_NUM_CONDITIONS2___
    -> N70W180
N70W180: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [70,90]
      NUM_TEST $(GEOM_maxLON) RANGE [-180,-150]
      NUM_TEST $(GEOM_maxLAT) RANGE [70,90]
      NUM_TEST $(GEOM_minLON) RANGE [-180,-150]
      NUM_TEST $(GEOM_minLAT) RANGE [70,90]
      NUM_TEST $(GEOM_minLON) RANGE [-180,-150]
      NUM_TEST $(GEOM_minLAT) RANGE [70,90]
      NUM_TEST $(GEOM_maxLON) RANGE [-180,-150]",<pass>
    <pass> -> FeatureReader_48 [INITIATOR]
FeatureReader_48
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_10
    ATTR_TABLE = SET_TO dataset_loc = FME_CONDITIONAL:DEFAULT_VALUE'fme://fme-server/70n150w_20101117_gmted_dsc075.tif?id=FME_SHAREDRESOURCE_DATA%2Ffilesys%2FHGDE%2FDEM%2FN70%2F70n150w_20101117_gmted_dsc075.tif&module=fmeserver&webservice=FME%20Server&connection=geopol'BOOL_OP;OR;COMPOSITE_TEST;1;TEST $(SERVER_MODE) = NO'$(FME_MF_DIR_ENCODED)DEM\N70\70n150w_20101117_gmted_dsc075.tif'FME_NUM_CONDITIONS2___
    -> N70W150
N70W150: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [70,90]
      NUM_TEST $(GEOM_maxLON) RANGE [-150,-120]
      NUM_TEST $(GEOM_maxLAT) RANGE [70,90]
      NUM_TEST $(GEOM_minLON) RANGE [-150,-120]
      NUM_TEST $(GEOM_minLAT) RANGE [70,90]
      NUM_TEST $(GEOM_minLON) RANGE [-150,-120]
      NUM_TEST $(GEOM_minLAT) RANGE [70,90]
      NUM_TEST $(GEOM_maxLON) RANGE [-150,-120]",<pass>
    <pass> -> FeatureReader_47 [INITIATOR]
FeatureReader_47
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_11
    ATTR_TABLE = SET_TO dataset_loc = FME_CONDITIONAL:DEFAULT_VALUE'fme://fme-server/70n120e_20101117_gmted_dsc075.tif?id=FME_SHAREDRESOURCE_DATA%2Ffilesys%2FHGDE%2FDEM%2FN70%2F70n120w_20101117_gmted_dsc075.tif&module=fmeserver&webservice=FME%20Server&connection=geopol'BOOL_OP;OR;COMPOSITE_TEST;1;TEST $(SERVER_MODE) = NO'$(FME_MF_DIR_ENCODED)DEM\N70\70n120w_20101117_gmted_dsc075.tif'FME_NUM_CONDITIONS2___
    -> N70W120
N70W120: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [70,90]
      NUM_TEST $(GEOM_maxLON) RANGE [-120,-90]
      NUM_TEST $(GEOM_maxLAT) RANGE [70,90]
      NUM_TEST $(GEOM_minLON) RANGE [-120,-90]
      NUM_TEST $(GEOM_minLAT) RANGE [70,90]
      NUM_TEST $(GEOM_minLON) RANGE [-120,-90]
      NUM_TEST $(GEOM_minLAT) RANGE [70,90]
      NUM_TEST $(GEOM_maxLON) RANGE [-120,-90]",<pass>
    <pass> -> FeatureReader_46 [INITIATOR]
FeatureReader_46
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_12
    ATTR_TABLE = SET_TO dataset_loc = FME_CONDITIONAL:DEFAULT_VALUE'fme://fme-server/70n090w_20101117_gmted_dsc075.tif?id=FME_SHAREDRESOURCE_DATA%2Ffilesys%2FHGDE%2FDEM%2FN70%2F70n090w_20101117_gmted_dsc075.tif&module=fmeserver&webservice=FME%20Server&connection=geopol'BOOL_OP;OR;COMPOSITE_TEST;1;TEST $(SERVER_MODE) = NO'$(FME_MF_DIR_ENCODED)DEM\N70\70n090w_20101117_gmted_dsc075.tif'FME_NUM_CONDITIONS2___
    -> N70W90
N70W90: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [70,90]
      NUM_TEST $(GEOM_maxLON) RANGE [-90,-60]
      NUM_TEST $(GEOM_maxLAT) RANGE [70,90]
      NUM_TEST $(GEOM_minLON) RANGE [-90,-60]
      NUM_TEST $(GEOM_minLAT) RANGE [70,90]
      NUM_TEST $(GEOM_minLON) RANGE [-90,-60]
      NUM_TEST $(GEOM_minLAT) RANGE [70,90]
      NUM_TEST $(GEOM_maxLON) RANGE [-90,-60]",<pass>
    <pass> -> FeatureReader_45 [INITIATOR]
FeatureReader_45
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_13
    ATTR_TABLE = SET_TO dataset_loc = FME_CONDITIONAL:DEFAULT_VALUE'fme://fme-server/70n060w_20101117_gmted_dsc075.tif?id=FME_SHAREDRESOURCE_DATA%2Ffilesys%2FHGDE%2FDEM%2FN70%2F70n060w_20101117_gmted_dsc075.tif&module=fmeserver&webservice=FME%20Server&connection=geopol'BOOL_OP;OR;COMPOSITE_TEST;1;TEST $(SERVER_MODE) = NO'$(FME_MF_DIR_ENCODED)DEM\N70\70n060w_20101117_gmted_dsc075.tif'FME_NUM_CONDITIONS2___
    -> N70W60
N70W60: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [70,90]
      NUM_TEST $(GEOM_maxLON) RANGE [-60,-30]
      NUM_TEST $(GEOM_maxLAT) RANGE [70,90]
      NUM_TEST $(GEOM_minLON) RANGE [-60,-30]
      NUM_TEST $(GEOM_minLAT) RANGE [70,90]
      NUM_TEST $(GEOM_minLON) RANGE [-60,-30]
      NUM_TEST $(GEOM_minLAT) RANGE [70,90]
      NUM_TEST $(GEOM_maxLON) RANGE [-60,-30]",<pass>
    <pass> -> FeatureReader_44 [INITIATOR]
FeatureReader_44
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_14
    ATTR_TABLE = SET_TO dataset_loc = FME_CONDITIONAL:DEFAULT_VALUE'fme://fme-server/70n030w_20101117_gmted_dsc075.tif?id=FME_SHAREDRESOURCE_DATA%2Ffilesys%2FHGDE%2FDEM%2FN70%2F70n030w_20101117_gmted_dsc075.tif&module=fmeserver&webservice=FME%20Server&connection=geopol'BOOL_OP;OR;COMPOSITE_TEST;1;TEST $(SERVER_MODE) = NO'$(FME_MF_DIR_ENCODED)DEM\N70\70n030w_20101117_gmted_dsc075.tif'FME_NUM_CONDITIONS2___
    -> N70W30
N70W30: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [70,90]
      NUM_TEST $(GEOM_maxLON) RANGE [-30,0]
      NUM_TEST $(GEOM_maxLAT) RANGE [70,90]
      NUM_TEST $(GEOM_minLON) RANGE [-30,0]
      NUM_TEST $(GEOM_minLAT) RANGE [70,90]
      NUM_TEST $(GEOM_minLON) RANGE [-30,0]
      NUM_TEST $(GEOM_minLAT) RANGE [70,90]
      NUM_TEST $(GEOM_maxLON) RANGE [-30,0]",<pass>
    <pass> -> FeatureReader_39 [INITIATOR]
FeatureReader_39
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_15
    ATTR_TABLE = SET_TO dataset_loc = FME_CONDITIONAL:DEFAULT_VALUE'fme://fme-server/50n000e_20101117_gmted_dsc075.tif?id=FME_SHAREDRESOURCE_DATA%2Ffilesys%2FHGDE%2FDEM%2FN50%2F50n000e_20101117_gmted_dsc075.tif&module=fmeserver&webservice=FME%20Server&connection=geopol'BOOL_OP;OR;COMPOSITE_TEST;1;TEST $(SERVER_MODE) = NO'$(FME_MF_DIR_ENCODED)DEM\N50\50n000e_20101117_gmted_dsc075.tif'FME_NUM_CONDITIONS2___
    -> N50E0
N50E0: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [50,70]
      NUM_TEST $(GEOM_maxLON) RANGE [0,30]
      NUM_TEST $(GEOM_maxLAT) RANGE [50,70]
      NUM_TEST $(GEOM_minLON) RANGE [0,30]
      NUM_TEST $(GEOM_minLAT) RANGE [50,70]
      NUM_TEST $(GEOM_minLON) RANGE [0,30]
      NUM_TEST $(GEOM_minLAT) RANGE [50,70]
      NUM_TEST $(GEOM_maxLON) RANGE [0,30]",<pass>
    <pass> -> FeatureReader_26 [INITIATOR]
FeatureReader_26
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_16
    ATTR_TABLE = SET_TO dataset_loc = FME_CONDITIONAL:DEFAULT_VALUE'fme://fme-server/50n030e_20101117_gmted_dsc075.tif?id=FME_SHAREDRESOURCE_DATA%2Ffilesys%2FHGDE%2FDEM%2FN50%2F50n030e_20101117_gmted_dsc075.tif&module=fmeserver&webservice=FME%20Server&connection=geopol'BOOL_OP;OR;COMPOSITE_TEST;1;TEST $(SERVER_MODE) = NO'$(FME_MF_DIR_ENCODED)DEM\N50\50n030e_20101117_gmted_dsc075.tif'FME_NUM_CONDITIONS2___
    -> N50E30
N50E30: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [50,70]
      NUM_TEST $(GEOM_maxLON) RANGE [30,60]
      NUM_TEST $(GEOM_maxLAT) RANGE [50,70]
      NUM_TEST $(GEOM_minLON) RANGE [30,60]
      NUM_TEST $(GEOM_minLAT) RANGE [50,70]
      NUM_TEST $(GEOM_minLON) RANGE [30,60]
      NUM_TEST $(GEOM_minLAT) RANGE [50,70]
      NUM_TEST $(GEOM_maxLON) RANGE [30,60]",<pass>
    <pass> -> FeatureReader_25 [INITIATOR]
FeatureReader_25
    ATTR_ACCUM_MODE = Only Use Result
    COMBINE_GEOM = Use Result
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_17
    ATTR_TABLE = SET_TO dataset_loc = FME_CONDITIONAL:DEFAULT_VALUE'fme://fme-server/50n060e_20101117_gmted_dsc075.tif?id=FME_SHAREDRESOURCE_DATA%2Ffilesys%2FHGDE%2FDEM%2FN50%2F50n060e_20101117_gmted_dsc075.tif&module=fmeserver&webservice=FME%20Server&connection=geopol'BOOL_OP;OR;COMPOSITE_TEST;1;TEST $(SERVER_MODE) = NO'$(FME_MF_DIR_ENCODED)DEM\N50\50n060e_20101117_gmted_dsc075.tif'FME_NUM_CONDITIONS2___
    -> N50E60
N50E60: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [50,70]
      NUM_TEST $(GEOM_maxLON) RANGE [60,90]
      NUM_TEST $(GEOM_maxLAT) RANGE [50,70]
      NUM_TEST $(GEOM_minLON) RANGE [60,90]
      NUM_TEST $(GEOM_minLAT) RANGE [50,70]
      NUM_TEST $(GEOM_minLON) RANGE [60,90]
      NUM_TEST $(GEOM_minLAT) RANGE [50,70]
      NUM_TEST $(GEOM_maxLON) RANGE [60,90]",<pass>
    <pass> -> FeatureReader_28 [INITIATOR]
FeatureReader_28
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_18
    ATTR_TABLE = SET_TO dataset_loc = FME_CONDITIONAL:DEFAULT_VALUE'fme://fme-server/50n090e_20101117_gmted_dsc075.tif?id=FME_SHAREDRESOURCE_DATA%2Ffilesys%2FHGDE%2FDEM%2FN50%2F50n090e_20101117_gmted_dsc075.tif&module=fmeserver&webservice=FME%20Server&connection=geopol'BOOL_OP;OR;COMPOSITE_TEST;1;TEST $(SERVER_MODE) = NO'$(FME_MF_DIR_ENCODED)DEM\N50\50n090e_20101117_gmted_dsc075.tif'FME_NUM_CONDITIONS2___
    -> N50E90
N50E90: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [50,70]
      NUM_TEST $(GEOM_maxLON) RANGE [90,120]
      NUM_TEST $(GEOM_maxLAT) RANGE [50,70]
      NUM_TEST $(GEOM_minLON) RANGE [90,120]
      NUM_TEST $(GEOM_minLAT) RANGE [50,70]
      NUM_TEST $(GEOM_minLON) RANGE [90,120]
      NUM_TEST $(GEOM_minLAT) RANGE [50,70]
      NUM_TEST $(GEOM_maxLON) RANGE [90,120]",<pass>
    <pass> -> FeatureReader_29 [INITIATOR]
FeatureReader_29
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_19
    ATTR_TABLE = SET_TO dataset_loc = FME_CONDITIONAL:DEFAULT_VALUE'fme://fme-server/50n120e_20101117_gmted_dsc075.tif?id=FME_SHAREDRESOURCE_DATA%2Ffilesys%2FHGDE%2FDEM%2FN50%2F30n120e_20101117_gmted_dsc075.tif&module=fmeserver&webservice=FME%20Server&connection=geopol'BOOL_OP;OR;COMPOSITE_TEST;1;TEST $(SERVER_MODE) = NO'$(FME_MF_DIR_ENCODED)DEM\N50\50n120e_20101117_gmted_dsc075.tif'FME_NUM_CONDITIONS2___
    -> N50E120
N50E120: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [50,70]
      NUM_TEST $(GEOM_maxLON) RANGE [120,150]
      NUM_TEST $(GEOM_maxLAT) RANGE [50,70]
      NUM_TEST $(GEOM_minLON) RANGE [120,150]
      NUM_TEST $(GEOM_minLAT) RANGE [50,70]
      NUM_TEST $(GEOM_minLON) RANGE [120,150]
      NUM_TEST $(GEOM_minLAT) RANGE [50,70]
      NUM_TEST $(GEOM_maxLON) RANGE [120,150]",<pass>
    <pass> -> FeatureReader_30 [INITIATOR]
FeatureReader_30
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_20
    ATTR_TABLE = SET_TO dataset_loc = FME_CONDITIONAL:DEFAULT_VALUE'fme://fme-server/50n150e_20101117_gmted_dsc075.tif?id=FME_SHAREDRESOURCE_DATA%2Ffilesys%2FHGDE%2FDEM%2FN50%2F50n150e_20101117_gmted_dsc075.tif&module=fmeserver&webservice=FME%20Server&connection=geopol'BOOL_OP;OR;COMPOSITE_TEST;1;TEST $(SERVER_MODE) = NO'$(FME_MF_DIR_ENCODED)DEM\N50\50n150e_20101117_gmted_dsc075.tif'FME_NUM_CONDITIONS2___
    -> N50E150
N50E150: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [50,70]
      NUM_TEST $(GEOM_maxLON) RANGE [150,180]
      NUM_TEST $(GEOM_maxLAT) RANGE [50,70]
      NUM_TEST $(GEOM_minLON) RANGE [150,180]
      NUM_TEST $(GEOM_minLAT) RANGE [50,70]
      NUM_TEST $(GEOM_minLON) RANGE [150,180]
      NUM_TEST $(GEOM_minLAT) RANGE [50,70]
      NUM_TEST $(GEOM_maxLON) RANGE [150,180]",<pass>
    <pass> -> FeatureReader_31 [INITIATOR]
FeatureReader_31
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_21
    ATTR_TABLE = SET_TO dataset_loc = FME_CONDITIONAL:DEFAULT_VALUE'fme://fme-server/50n180e_20101117_gmted_dsc075.tif?id=FME_SHAREDRESOURCE_DATA%2Ffilesys%2FHGDE%2FDEM%2FN50%2F50n180e_20101117_gmted_dsc075.tif&module=fmeserver&webservice=FME%20Server&connection=geopol'BOOL_OP;OR;COMPOSITE_TEST;1;TEST $(SERVER_MODE) = NO'$(FME_MF_DIR_ENCODED)DEM\N50\50n180w_20101117_gmted_dsc075.tif'FME_NUM_CONDITIONS2___
    -> N50W180
N50W180: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [50,70]
      NUM_TEST $(GEOM_maxLON) RANGE [-180,-150]
      NUM_TEST $(GEOM_maxLAT) RANGE [50,70]
      NUM_TEST $(GEOM_minLON) RANGE [-180,-150]
      NUM_TEST $(GEOM_minLAT) RANGE [50,70]
      NUM_TEST $(GEOM_minLON) RANGE [-180,-150]
      NUM_TEST $(GEOM_minLAT) RANGE [50,70]
      NUM_TEST $(GEOM_maxLON) RANGE [-180,-150]",<pass>
    <pass> -> FeatureReader_36 [INITIATOR]
FeatureReader_36
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_22
    ATTR_TABLE = SET_TO dataset_loc = FME_CONDITIONAL:DEFAULT_VALUE'fme://fme-server/50n150w_20101117_gmted_dsc075.tif?id=FME_SHAREDRESOURCE_DATA%2Ffilesys%2FHGDE%2FDEM%2FN50%2F50n150w_20101117_gmted_dsc075.tif&module=fmeserver&webservice=FME%20Server&connection=geopol'BOOL_OP;OR;COMPOSITE_TEST;1;TEST $(SERVER_MODE) = NO'$(FME_MF_DIR_ENCODED)DEM\N50\50n150w_20101117_gmted_dsc075.tif'FME_NUM_CONDITIONS2___
    -> N50W150
N50W150: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [50,70]
      NUM_TEST $(GEOM_maxLON) RANGE [-150,-120]
      NUM_TEST $(GEOM_maxLAT) RANGE [50,70]
      NUM_TEST $(GEOM_minLON) RANGE [-150,-120]
      NUM_TEST $(GEOM_minLAT) RANGE [50,70]
      NUM_TEST $(GEOM_minLON) RANGE [-150,-120]
      NUM_TEST $(GEOM_minLAT) RANGE [50,70]
      NUM_TEST $(GEOM_maxLON) RANGE [-150,-120]",<pass>
    <pass> -> FeatureReader_35 [INITIATOR]
FeatureReader_35
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_23
    ATTR_TABLE = SET_TO dataset_loc = FME_CONDITIONAL:DEFAULT_VALUE'fme://fme-server/50n120w_20101117_gmted_dsc075.tif?id=FME_SHAREDRESOURCE_DATA%2Ffilesys%2FHGDE%2FDEM%2FN50%2F50n120w_20101117_gmted_dsc075.tif&module=fmeserver&webservice=FME%20Server&connection=geopol'BOOL_OP;OR;COMPOSITE_TEST;1;TEST $(SERVER_MODE) = NO'$(FME_MF_DIR_ENCODED)DEM\N50\50n120w_20101117_gmted_dsc075.tif'FME_NUM_CONDITIONS2___
    -> N50W120
N50W120: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [50,70]
      NUM_TEST $(GEOM_maxLON) RANGE [-120,-90]
      NUM_TEST $(GEOM_maxLAT) RANGE [50,70]
      NUM_TEST $(GEOM_minLON) RANGE [-120,-90]
      NUM_TEST $(GEOM_minLAT) RANGE [50,70]
      NUM_TEST $(GEOM_minLON) RANGE [-120,-90]
      NUM_TEST $(GEOM_minLAT) RANGE [50,70]
      NUM_TEST $(GEOM_maxLON) RANGE [-120,-90]",<pass>
    <pass> -> FeatureReader_34 [INITIATOR]
FeatureReader_34
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_24
    ATTR_TABLE = SET_TO dataset_loc = FME_CONDITIONAL:DEFAULT_VALUE'fme://fme-server/50n090w_20101117_gmted_dsc075.tif?id=FME_SHAREDRESOURCE_DATA%2Ffilesys%2FHGDE%2FDEM%2FN50%2F50n090w_20101117_gmted_dsc075.tif&module=fmeserver&webservice=FME%20Server&connection=geopol'BOOL_OP;OR;COMPOSITE_TEST;1;TEST $(SERVER_MODE) = NO'$(FME_MF_DIR_ENCODED)DEM\N50\50n090w_20101117_gmted_dsc075.tif'FME_NUM_CONDITIONS2___
    -> N50W90
N50W90: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [50,70]
      NUM_TEST $(GEOM_maxLON) RANGE [-90,-60]
      NUM_TEST $(GEOM_maxLAT) RANGE [50,70]
      NUM_TEST $(GEOM_minLON) RANGE [-90,-60]
      NUM_TEST $(GEOM_minLAT) RANGE [50,70]
      NUM_TEST $(GEOM_minLON) RANGE [-90,-60]
      NUM_TEST $(GEOM_minLAT) RANGE [50,70]
      NUM_TEST $(GEOM_maxLON) RANGE [-90,-60]",<pass>
    <pass> -> FeatureReader_33 [INITIATOR]
FeatureReader_33
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_25
    ATTR_TABLE = SET_TO dataset_loc = FME_CONDITIONAL:DEFAULT_VALUE'fme://fme-server/50n060w_20101117_gmted_dsc075.tif?id=FME_SHAREDRESOURCE_DATA%2Ffilesys%2FHGDE%2FDEM%2FN50%2F50n060w_20101117_gmted_dsc075.tif&module=fmeserver&webservice=FME%20Server&connection=geopol'BOOL_OP;OR;COMPOSITE_TEST;1;TEST $(SERVER_MODE) = NO'$(FME_MF_DIR_ENCODED)DEM\N50\50n060w_20101117_gmted_dsc075.tif'FME_NUM_CONDITIONS2___
    -> N50W60
N50W60: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [50,70]
      NUM_TEST $(GEOM_maxLON) RANGE [-60,-30]
      NUM_TEST $(GEOM_maxLAT) RANGE [50,70]
      NUM_TEST $(GEOM_minLON) RANGE [-60,-30]
      NUM_TEST $(GEOM_minLAT) RANGE [50,70]
      NUM_TEST $(GEOM_minLON) RANGE [-60,-30]
      NUM_TEST $(GEOM_minLAT) RANGE [50,70]
      NUM_TEST $(GEOM_maxLON) RANGE [-60,-30]",<pass>
    <pass> -> FeatureReader_32 [INITIATOR]
FeatureReader_32
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_26
    ATTR_TABLE = SET_TO dataset_loc = FME_CONDITIONAL:DEFAULT_VALUE'fme://fme-server/50n030w_20101117_gmted_dsc075.tif?id=FME_SHAREDRESOURCE_DATA%2Ffilesys%2FHGDE%2FDEM%2FN50%2F50n030w_20101117_gmted_dsc075.tif&module=fmeserver&webservice=FME%20Server&connection=geopol'BOOL_OP;OR;COMPOSITE_TEST;1;TEST $(SERVER_MODE) = NO'$(FME_MF_DIR_ENCODED)DEM\N50\50n030w_20101117_gmted_dsc075.tif'FME_NUM_CONDITIONS2___
    -> N50W30
N50W30: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [50,70]
      NUM_TEST $(GEOM_maxLON) RANGE [-30,0]
      NUM_TEST $(GEOM_maxLAT) RANGE [50,70]
      NUM_TEST $(GEOM_minLON) RANGE [-30,0]
      NUM_TEST $(GEOM_minLAT) RANGE [50,70]
      NUM_TEST $(GEOM_minLON) RANGE [-30,0]
      NUM_TEST $(GEOM_minLAT) RANGE [50,70]
      NUM_TEST $(GEOM_maxLON) RANGE [-30,0]",<pass>
    <pass> -> FeatureReader_27 [INITIATOR]
FeatureReader_27
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager
    ATTR_TABLE = SET_TO dataset_loc = FME_CONDITIONAL:DEFAULT_VALUE'fme://fme-server/30n000e_20101117_gmted_dsc075.tif?id=FME_SHAREDRESOURCE_DATA%2Ffilesys%2FHGDE%2FDEM%2FN30%2F30n000e_20101117_gmted_dsc075.tif&module=fmeserver&webservice=FME%20Server&connection=geopol'BOOL_OP;OR;COMPOSITE_TEST;1;TEST $(SERVER_MODE) = NO'$(FME_MF_DIR_ENCODED)DEM\N30\30n000e_20101117_gmted_dsc075.tif'FME_NUM_CONDITIONS2___
    -> N30E0
N30E0: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [30,50]
      NUM_TEST $(GEOM_maxLON) RANGE [0,30]
      NUM_TEST $(GEOM_maxLAT) RANGE [30,50]
      NUM_TEST $(GEOM_minLON) RANGE [0,30]
      NUM_TEST $(GEOM_minLAT) RANGE [30,50]
      NUM_TEST $(GEOM_minLON) RANGE [0,30]
      NUM_TEST $(GEOM_minLAT) RANGE [30,50]
      NUM_TEST $(GEOM_maxLON) RANGE [0,30]",<pass>
    <pass> -> FeatureReader_14 [INITIATOR]
FeatureReader_14
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_2
    ATTR_TABLE = SET_TO dataset_loc = FME_CONDITIONAL:DEFAULT_VALUE'fme://fme-server/30n030e_20101117_gmted_dsc075.tif?id=FME_SHAREDRESOURCE_DATA%2Ffilesys%2FHGDE%2FDEM%2FN30%2F30n030e_20101117_gmted_dsc075.tif&module=fmeserver&webservice=FME%20Server&connection=geopol'BOOL_OP;OR;COMPOSITE_TEST;1;TEST $(SERVER_MODE) = NO'$(FME_MF_DIR_ENCODED)DEM\N30\30n030e_20101117_gmted_dsc075.tif'FME_NUM_CONDITIONS2___
    -> N30E30
N30E30: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [30,50]
      NUM_TEST $(GEOM_maxLON) RANGE [30,60]
      NUM_TEST $(GEOM_maxLAT) RANGE [30,50]
      NUM_TEST $(GEOM_minLON) RANGE [30,60]
      NUM_TEST $(GEOM_minLAT) RANGE [30,50]
      NUM_TEST $(GEOM_minLON) RANGE [30,60]
      NUM_TEST $(GEOM_minLAT) RANGE [30,50]
      NUM_TEST $(GEOM_maxLON) RANGE [30,60]",<pass>
    <pass> -> FeatureReader_13 [INITIATOR]
FeatureReader_13
    ATTR_ACCUM_MODE = Only Use Result
    COMBINE_GEOM = Use Result
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_27
    ATTR_TABLE = SET_TO dataset_loc = FME_CONDITIONAL:DEFAULT_VALUE'fme://fme-server/30n060e_20101117_gmted_dsc075.tif?id=FME_SHAREDRESOURCE_DATA%2Ffilesys%2FHGDE%2FDEM%2FN30%2F30n060e_20101117_gmted_dsc075.tif&module=fmeserver&webservice=FME%20Server&connection=geopol'BOOL_OP;OR;COMPOSITE_TEST;1;TEST $(SERVER_MODE) = NO'$(FME_MF_DIR_ENCODED)DEM\N30\30n060e_20101117_gmted_dsc075.tif'FME_NUM_CONDITIONS2___
    -> N30E60
N30E60: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [30,50]
      NUM_TEST $(GEOM_maxLON) RANGE [60,90]
      NUM_TEST $(GEOM_maxLAT) RANGE [30,50]
      NUM_TEST $(GEOM_minLON) RANGE [60,90]
      NUM_TEST $(GEOM_minLAT) RANGE [30,50]
      NUM_TEST $(GEOM_minLON) RANGE [60,90]
      NUM_TEST $(GEOM_minLAT) RANGE [30,50]
      NUM_TEST $(GEOM_maxLON) RANGE [60,90]",<pass>
    <pass> -> FeatureReader_16 [INITIATOR]
FeatureReader_16
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_28
    ATTR_TABLE = SET_TO dataset_loc = FME_CONDITIONAL:DEFAULT_VALUE'fme://fme-server/30n090e_20101117_gmted_dsc075.tif?id=FME_SHAREDRESOURCE_DATA%2Ffilesys%2FHGDE%2FDEM%2FN30%2F30n090e_20101117_gmted_dsc075.tif&module=fmeserver&webservice=FME%20Server&connection=geopol'BOOL_OP;OR;COMPOSITE_TEST;1;TEST $(SERVER_MODE) = NO'$(FME_MF_DIR_ENCODED)DEM\N30\30n090e_20101117_gmted_dsc075.tif'FME_NUM_CONDITIONS2___
    -> N30E90
N30E90: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [30,50]
      NUM_TEST $(GEOM_maxLON) RANGE [90,120]
      NUM_TEST $(GEOM_maxLAT) RANGE [30,50]
      NUM_TEST $(GEOM_minLON) RANGE [90,120]
      NUM_TEST $(GEOM_minLAT) RANGE [30,50]
      NUM_TEST $(GEOM_minLON) RANGE [90,120]
      NUM_TEST $(GEOM_minLAT) RANGE [30,50]
      NUM_TEST $(GEOM_maxLON) RANGE [90,120]",<pass>
    <pass> -> FeatureReader_17 [INITIATOR]
FeatureReader_17
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_29
    ATTR_TABLE = SET_TO dataset_loc = FME_CONDITIONAL:DEFAULT_VALUE'fme://fme-server/30n120e_20101117_gmted_dsc075.tif?id=FME_SHAREDRESOURCE_DATA%2Ffilesys%2FHGDE%2FDEM%2FN30%2F30n120e_20101117_gmted_dsc075.tif&module=fmeserver&webservice=FME%20Server&connection=geopol'BOOL_OP;OR;COMPOSITE_TEST;1;TEST $(SERVER_MODE) = NO'$(FME_MF_DIR_ENCODED)DEM\N30\30n120e_20101117_gmted_dsc075.tif'FME_NUM_CONDITIONS2___
    -> N30E120
N30E120: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [30,50]
      NUM_TEST $(GEOM_maxLON) RANGE [120,150]
      NUM_TEST $(GEOM_maxLAT) RANGE [30,50]
      NUM_TEST $(GEOM_minLON) RANGE [120,150]
      NUM_TEST $(GEOM_minLAT) RANGE [30,50]
      NUM_TEST $(GEOM_minLON) RANGE [120,150]
      NUM_TEST $(GEOM_minLAT) RANGE [30,50]
      NUM_TEST $(GEOM_maxLON) RANGE [120,150]",<pass>
    <pass> -> FeatureReader_18 [INITIATOR]
FeatureReader_18
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_30
    ATTR_TABLE = SET_TO dataset_loc = FME_CONDITIONAL:DEFAULT_VALUE'fme://fme-server/30n150e_20101117_gmted_dsc075.tif?id=FME_SHAREDRESOURCE_DATA%2Ffilesys%2FHGDE%2FDEM%2FN30%2F30n150e_20101117_gmted_dsc075.tif&module=fmeserver&webservice=FME%20Server&connection=geopol'BOOL_OP;OR;COMPOSITE_TEST;1;TEST $(SERVER_MODE) = NO'$(FME_MF_DIR_ENCODED)DEM\N30\30n150e_20101117_gmted_dsc075.tif'FME_NUM_CONDITIONS2___
    -> N30E150
N30E150: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [30,50]
      NUM_TEST $(GEOM_maxLON) RANGE [150,180]
      NUM_TEST $(GEOM_maxLAT) RANGE [30,50]
      NUM_TEST $(GEOM_minLON) RANGE [150,180]
      NUM_TEST $(GEOM_minLAT) RANGE [30,50]
      NUM_TEST $(GEOM_minLON) RANGE [150,180]
      NUM_TEST $(GEOM_minLAT) RANGE [30,50]
      NUM_TEST $(GEOM_maxLON) RANGE [150,180]",<pass>
    <pass> -> FeatureReader_19 [INITIATOR]
FeatureReader_19
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_31
    ATTR_TABLE = SET_TO dataset_loc = FME_CONDITIONAL:DEFAULT_VALUE'fme://fme-server/30n180w_20101117_gmted_dsc075.tif?id=FME_SHAREDRESOURCE_DATA%2Ffilesys%2FHGDE%2FDEM%2FN30%2F30n180w_20101117_gmted_dsc075.tif&module=fmeserver&webservice=FME%20Server&connection=geopol'BOOL_OP;OR;COMPOSITE_TEST;1;TEST $(SERVER_MODE) = NO'$(FME_MF_DIR_ENCODED)DEM\N30\30n180w_20101117_gmted_dsc075.tif'FME_NUM_CONDITIONS2___
    -> N30W180
N30W180: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [30,50]
      NUM_TEST $(GEOM_maxLON) RANGE [-180,-150]
      NUM_TEST $(GEOM_maxLAT) RANGE [30,50]
      NUM_TEST $(GEOM_minLON) RANGE [-180,-150]
      NUM_TEST $(GEOM_minLAT) RANGE [30,50]
      NUM_TEST $(GEOM_minLON) RANGE [-180,-150]
      NUM_TEST $(GEOM_minLAT) RANGE [30,60]
      NUM_TEST $(GEOM_maxLON) RANGE [-180,-150]",<pass>
    <pass> -> FeatureReader_24 [INITIATOR]
FeatureReader_24
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_32
    ATTR_TABLE = SET_TO dataset_loc = FME_CONDITIONAL:DEFAULT_VALUE'fme://fme-server/30n150w_20101117_gmted_dsc075.tif?id=FME_SHAREDRESOURCE_DATA%2Ffilesys%2FHGDE%2FDEM%2FN30%2F30n150w_20101117_gmted_dsc075.tif&module=fmeserver&webservice=FME%20Server&connection=geopol'BOOL_OP;OR;COMPOSITE_TEST;1;TEST $(SERVER_MODE) = NO'$(FME_MF_DIR_ENCODED)DEM\N30\30n150w_20101117_gmted_dsc075.tif'FME_NUM_CONDITIONS2___
    -> N30W150
N30W150: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [30,50]
      NUM_TEST $(GEOM_maxLON) RANGE [-150,-120]
      NUM_TEST $(GEOM_maxLAT) RANGE [30,50]
      NUM_TEST $(GEOM_minLON) RANGE [-150,-120]
      NUM_TEST $(GEOM_minLAT) RANGE [30,50]
      NUM_TEST $(GEOM_minLON) RANGE [-150,-120]
      NUM_TEST $(GEOM_minLAT) RANGE [30,50]
      NUM_TEST $(GEOM_maxLON) RANGE [-150,-120]",<pass>
    <pass> -> FeatureReader_23 [INITIATOR]
FeatureReader_23
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_33
    ATTR_TABLE = SET_TO dataset_loc = FME_CONDITIONAL:DEFAULT_VALUE'fme://fme-server/30n120w_20101117_gmted_dsc075.tif?id=FME_SHAREDRESOURCE_DATA%2Ffilesys%2FHGDE%2FDEM%2FN30%2F30n120w_20101117_gmted_dsc075.tif&module=fmeserver&webservice=FME%20Server&connection=geopol'BOOL_OP;OR;COMPOSITE_TEST;1;TEST $(SERVER_MODE) = NO'$(FME_MF_DIR_ENCODED)DEM\N30\30n120w_20101117_gmted_dsc075.tif'FME_NUM_CONDITIONS2___
    -> N30W120
N30W120: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [30,50]
      NUM_TEST $(GEOM_maxLON) RANGE [-120,-90]
      NUM_TEST $(GEOM_maxLAT) RANGE [30,50]
      NUM_TEST $(GEOM_minLON) RANGE [-120,-90]
      NUM_TEST $(GEOM_minLAT) RANGE [30,50]
      NUM_TEST $(GEOM_minLON) RANGE [-120,-90]
      NUM_TEST $(GEOM_minLAT) RANGE [30,50]
      NUM_TEST $(GEOM_maxLON) RANGE [-120,-90]",<pass>
    <pass> -> FeatureReader_22 [INITIATOR]
FeatureReader_22
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_34
    ATTR_TABLE = SET_TO dataset_loc = FME_CONDITIONAL:DEFAULT_VALUE'fme://fme-server/30n090w_20101117_gmted_dsc075.tif?id=FME_SHAREDRESOURCE_DATA%2Ffilesys%2FHGDE%2FDEM%2FN30%2F30n090w_20101117_gmted_dsc075.tif&module=fmeserver&webservice=FME%20Server&connection=geopol'BOOL_OP;OR;COMPOSITE_TEST;1;TEST $(SERVER_MODE) = NO'$(FME_MF_DIR_ENCODED)DEM\N30\30n090w_20101117_gmted_dsc075.tif'FME_NUM_CONDITIONS2___
    -> N30W90
N30W90: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [30,50]
      NUM_TEST $(GEOM_maxLON) RANGE [-90,-60]
      NUM_TEST $(GEOM_maxLAT) RANGE [30,50]
      NUM_TEST $(GEOM_minLON) RANGE [-90,-60]
      NUM_TEST $(GEOM_minLAT) RANGE [30,50]
      NUM_TEST $(GEOM_minLON) RANGE [-90,-60]
      NUM_TEST $(GEOM_minLAT) RANGE [30,50]
      NUM_TEST $(GEOM_maxLON) RANGE [-90,-60]",<pass>
    <pass> -> FeatureReader_21 [INITIATOR]
FeatureReader_21
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_35
    ATTR_TABLE = SET_TO dataset_loc = FME_CONDITIONAL:DEFAULT_VALUE'fme://fme-server/30n060w_20101117_gmted_dsc075.tif?id=FME_SHAREDRESOURCE_DATA%2Ffilesys%2FHGDE%2FDEM%2FN30%2F30n060w_20101117_gmted_dsc075.tif&module=fmeserver&webservice=FME%20Server&connection=geopol'BOOL_OP;OR;COMPOSITE_TEST;1;TEST $(SERVER_MODE) = NO'$(FME_MF_DIR_ENCODED)DEM\N30\30n060w_20101117_gmted_dsc075.tif'FME_NUM_CONDITIONS2___
    -> N30W60
N30W60: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [30,50]
      NUM_TEST $(GEOM_maxLON) RANGE [-60,-30]
      NUM_TEST $(GEOM_maxLAT) RANGE [30,50]
      NUM_TEST $(GEOM_minLON) RANGE [-60,-30]
      NUM_TEST $(GEOM_minLAT) RANGE [30,50]
      NUM_TEST $(GEOM_minLON) RANGE [-60,-30]
      NUM_TEST $(GEOM_minLAT) RANGE [30,50]
      NUM_TEST $(GEOM_maxLON) RANGE [-60,-30]",<pass>
    <pass> -> FeatureReader_20 [INITIATOR]
FeatureReader_20
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_36
    ATTR_TABLE = SET_TO dataset_loc = FME_CONDITIONAL:DEFAULT_VALUE'fme://fme-server/30n030w_20101117_gmted_dsc075.tif?id=FME_SHAREDRESOURCE_DATA%2Ffilesys%2FHGDE%2FDEM%2FN30%2F30n030w_20101117_gmted_dsc075.tif&module=fmeserver&webservice=FME%20Server&connection=geopol'BOOL_OP;OR;COMPOSITE_TEST;1;TEST $(SERVER_MODE) = NO'$(FME_MF_DIR_ENCODED)DEM\N30\30n030w_20101117_gmted_dsc075.tif'FME_NUM_CONDITIONS2___
    -> N30W30
N30W30: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [30,50]
      NUM_TEST $(GEOM_maxLON) RANGE [-30,0]
      NUM_TEST $(GEOM_maxLAT) RANGE [30,50]
      NUM_TEST $(GEOM_minLON) RANGE [-30,0]
      NUM_TEST $(GEOM_minLAT) RANGE [30,50]
      NUM_TEST $(GEOM_minLON) RANGE [-30,0]
      NUM_TEST $(GEOM_minLAT) RANGE [30,50]
      NUM_TEST $(GEOM_maxLON) RANGE [-30,0]",<pass>
    <pass> -> FeatureReader_15 [INITIATOR]
FeatureReader_15
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_37
    ATTR_TABLE = SET_TO dataset_loc = FME_CONDITIONAL:DEFAULT_VALUE'fme://fme-server/10n000e_20101117_gmted_dsc075.tif?id=FME_SHAREDRESOURCE_DATA%2Ffilesys%2FHGDE%2FDEM%2FN10%2F10n000e_20101117_gmted_dsc075.tif&module=fmeserver&webservice=FME%20Server&connection=geopol'BOOL_OP;OR;COMPOSITE_TEST;1;TEST $(SERVER_MODE) = NO'$(FME_MF_DIR_ENCODED)DEM\N10\10n000e_20101117_gmted_dsc075.tif'FME_NUM_CONDITIONS2___
    -> N10E0
N10E0: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [10,30]
      NUM_TEST $(GEOM_maxLON) RANGE [0,30]
      NUM_TEST $(GEOM_maxLAT) RANGE [10,30]
      NUM_TEST $(GEOM_minLON) RANGE [0,30]
      NUM_TEST $(GEOM_minLAT) RANGE [10,30]
      NUM_TEST $(GEOM_minLON) RANGE [0,30]
      NUM_TEST $(GEOM_minLAT) RANGE [10,30]
      NUM_TEST $(GEOM_maxLON) RANGE [0,30]",<pass>
    <pass> -> FeatureReader_2 [INITIATOR]
FeatureReader_2
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_38
    ATTR_TABLE = SET_TO dataset_loc = FME_CONDITIONAL:DEFAULT_VALUE'fme://fme-server/10n030e_20101117_gmted_dsc075.tif?id=FME_SHAREDRESOURCE_DATA%2Ffilesys%2FHGDE%2FDEM%2FN10%2F10n030e_20101117_gmted_dsc075.tif&module=fmeserver&webservice=FME%20Server&connection=geopol'BOOL_OP;OR;COMPOSITE_TEST;1;TEST $(SERVER_MODE) = NO'$(FME_MF_DIR_ENCODED)DEM\N10\10n030e_20101117_gmted_dsc075.tif'FME_NUM_CONDITIONS2___
    -> N10E30
N10E30: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [10,30]
      NUM_TEST $(GEOM_maxLON) RANGE [30,60]
      NUM_TEST $(GEOM_maxLAT) RANGE [10,30]
      NUM_TEST $(GEOM_minLON) RANGE [30,60]
      NUM_TEST $(GEOM_minLAT) RANGE [10,30]
      NUM_TEST $(GEOM_minLON) RANGE [30,60]
      NUM_TEST $(GEOM_minLAT) RANGE [10,30]
      NUM_TEST $(GEOM_maxLON) RANGE [30,60]",<pass>
    <pass> -> FeatureReader [INITIATOR]
FeatureReader
    ATTR_ACCUM_MODE = Only Use Result
    COMBINE_GEOM = Use Result
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_39
    ATTR_TABLE = SET_TO dataset_loc = FME_CONDITIONAL:DEFAULT_VALUE'fme://fme-server/10n060e_20101117_gmted_dsc075.tif?id=FME_SHAREDRESOURCE_DATA%2Ffilesys%2FHGDE%2FDEM%2FN10%2F10n060e_20101117_gmted_dsc075.tif&module=fmeserver&webservice=FME%20Server&connection=geopol'BOOL_OP;OR;COMPOSITE_TEST;1;TEST $(SERVER_MODE) = NO'$(FME_MF_DIR_ENCODED)DEM\N10\10n060e_20101117_gmted_dsc075.tif'FME_NUM_CONDITIONS2___
    -> N10E60
N10E60: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [10,30]
      NUM_TEST $(GEOM_maxLON) RANGE [60,90]
      NUM_TEST $(GEOM_maxLAT) RANGE [10,30]
      NUM_TEST $(GEOM_minLON) RANGE [60,90]
      NUM_TEST $(GEOM_minLAT) RANGE [10,30]
      NUM_TEST $(GEOM_minLON) RANGE [60,90]
      NUM_TEST $(GEOM_minLAT) RANGE [10,30]
      NUM_TEST $(GEOM_maxLON) RANGE [60,90]",<pass>
    <pass> -> FeatureReader_4 [INITIATOR]
FeatureReader_4
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_40
    ATTR_TABLE = SET_TO dataset_loc = FME_CONDITIONAL:DEFAULT_VALUE'fme://fme-server/10n090e_20101117_gmted_dsc075.tif?id=FME_SHAREDRESOURCE_DATA%2Ffilesys%2FHGDE%2FDEM%2FN10%2F10n090e_20101117_gmted_dsc075.tif&module=fmeserver&webservice=FME%20Server&connection=geopol'BOOL_OP;OR;COMPOSITE_TEST;1;TEST $(SERVER_MODE) = NO'$(FME_MF_DIR_ENCODED)DEM\N10\10n090e_20101117_gmted_dsc075.tif'FME_NUM_CONDITIONS2___
    -> N10E90
N10E90: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [10,30]
      NUM_TEST $(GEOM_maxLON) RANGE [90,120]
      NUM_TEST $(GEOM_maxLAT) RANGE [10,30]
      NUM_TEST $(GEOM_minLON) RANGE [90,120]
      NUM_TEST $(GEOM_minLAT) RANGE [10,30]
      NUM_TEST $(GEOM_minLON) RANGE [90,120]
      NUM_TEST $(GEOM_minLAT) RANGE [10,30]
      NUM_TEST $(GEOM_maxLON) RANGE [90,120]",<pass>
    <pass> -> FeatureReader_5 [INITIATOR]
FeatureReader_5
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_41
    ATTR_TABLE = SET_TO dataset_loc = FME_CONDITIONAL:DEFAULT_VALUE'fme://fme-server/10n120e_20101117_gmted_dsc075.tif?id=FME_SHAREDRESOURCE_DATA%2Ffilesys%2FHGDE%2FDEM%2FN10%2F10n120e_20101117_gmted_dsc075.tif&module=fmeserver&webservice=FME%20Server&connection=geopol'BOOL_OP;OR;COMPOSITE_TEST;1;TEST $(SERVER_MODE) = NO'$(FME_MF_DIR_ENCODED)DEM\N10\10n120e_20101117_gmted_dsc075.tif'FME_NUM_CONDITIONS2___
    -> N10E120
N10E120: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [10,30]
      NUM_TEST $(GEOM_maxLON) RANGE [120,150]
      NUM_TEST $(GEOM_maxLAT) RANGE [10,30]
      NUM_TEST $(GEOM_minLON) RANGE [120,150]
      NUM_TEST $(GEOM_minLAT) RANGE [10,30]
      NUM_TEST $(GEOM_minLON) RANGE [120,150]
      NUM_TEST $(GEOM_minLAT) RANGE [10,30]
      NUM_TEST $(GEOM_maxLON) RANGE [120,150]",<pass>
    <pass> -> FeatureReader_6 [INITIATOR]
FeatureReader_6
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_42
    ATTR_TABLE = SET_TO dataset_loc = FME_CONDITIONAL:DEFAULT_VALUE'fme://fme-server/10n150e_20101117_gmted_dsc075.tif?id=FME_SHAREDRESOURCE_DATA%2Ffilesys%2FHGDE%2FDEM%2FN10%2F10n150e_20101117_gmted_dsc075.tif&module=fmeserver&webservice=FME%20Server&connection=geopol'BOOL_OP;OR;COMPOSITE_TEST;1;TEST $(SERVER_MODE) = NO'$(FME_MF_DIR_ENCODED)DEM\N10\10n150e_20101117_gmted_dsc075.tif'FME_NUM_CONDITIONS2___
    -> N10E150
N10E150: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [10,30]
      NUM_TEST $(GEOM_maxLON) RANGE [150,180]
      NUM_TEST $(GEOM_maxLAT) RANGE [10,30]
      NUM_TEST $(GEOM_minLON) RANGE [150,180]
      NUM_TEST $(GEOM_minLAT) RANGE [10,30]
      NUM_TEST $(GEOM_minLON) RANGE [150,180]
      NUM_TEST $(GEOM_minLAT) RANGE [10,30]
      NUM_TEST $(GEOM_maxLON) RANGE [150,180]",<pass>
    <pass> -> FeatureReader_7 [INITIATOR]
FeatureReader_7
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_43
    ATTR_TABLE = SET_TO dataset_loc = FME_CONDITIONAL:DEFAULT_VALUE'fme://fme-server/10n180w_20101117_gmted_dsc075.tif?id=FME_SHAREDRESOURCE_DATA%2Ffilesys%2FHGDE%2FDEM%2FN10%2F10n180w_20101117_gmted_dsc075.tif&module=fmeserver&webservice=FME%20Server&connection=geopol'BOOL_OP;OR;COMPOSITE_TEST;1;TEST $(SERVER_MODE) = NO'$(FME_MF_DIR_ENCODED)DEM\N10\10n180w_20101117_gmted_dsc075.tif'FME_NUM_CONDITIONS2___
    -> N10W180
N10W180: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [10,30]
      NUM_TEST $(GEOM_maxLON) RANGE [-180,-150]
      NUM_TEST $(GEOM_maxLAT) RANGE [10,30]
      NUM_TEST $(GEOM_minLON) RANGE [-180,-150]
      NUM_TEST $(GEOM_minLAT) RANGE [10,30]
      NUM_TEST $(GEOM_minLON) RANGE [-180,-150]
      NUM_TEST $(GEOM_minLAT) RANGE [10,30]
      NUM_TEST $(GEOM_maxLON) RANGE [-180,-150]",<pass>
    <pass> -> FeatureReader_12 [INITIATOR]
FeatureReader_12
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_44
    ATTR_TABLE = SET_TO dataset_loc = FME_CONDITIONAL:DEFAULT_VALUE'fme://fme-server/10n150w_20101117_gmted_dsc075.tif?id=FME_SHAREDRESOURCE_DATA%2Ffilesys%2FHGDE%2FDEM%2FN10%2F10n150w_20101117_gmted_dsc075.tif&module=fmeserver&webservice=FME%20Server&connection=geopol'BOOL_OP;OR;COMPOSITE_TEST;1;TEST $(SERVER_MODE) = NO'$(FME_MF_DIR_ENCODED)DEM\N10\10n150w_20101117_gmted_dsc075.tif'FME_NUM_CONDITIONS2___
    -> N10W150
N10W150: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [10,30]
      NUM_TEST $(GEOM_maxLON) RANGE [-150,-120]
      NUM_TEST $(GEOM_maxLAT) RANGE [10,30]
      NUM_TEST $(GEOM_minLON) RANGE [-150,-120]
      NUM_TEST $(GEOM_minLAT) RANGE [10,30]
      NUM_TEST $(GEOM_minLON) RANGE [-150,-120]
      NUM_TEST $(GEOM_minLAT) RANGE [10,30]
      NUM_TEST $(GEOM_maxLON) RANGE [-150,-120]",<pass>
    <pass> -> FeatureReader_11 [INITIATOR]
FeatureReader_11
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_45
    ATTR_TABLE = SET_TO dataset_loc = FME_CONDITIONAL:DEFAULT_VALUE'fme://fme-server/10n120w_20101117_gmted_dsc075.tif?id=FME_SHAREDRESOURCE_DATA%2Ffilesys%2FHGDE%2FDEM%2FN10%2F10n120w_20101117_gmted_dsc075.tif&module=fmeserver&webservice=FME%20Server&connection=geopol'BOOL_OP;OR;COMPOSITE_TEST;1;TEST $(SERVER_MODE) = NO'$(FME_MF_DIR_ENCODED)DEM\N10\10n120w_20101117_gmted_dsc075.tif'FME_NUM_CONDITIONS2___
    -> N10W120
N10W120: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [10,30]
      NUM_TEST $(GEOM_maxLON) RANGE [-120,-90]
      NUM_TEST $(GEOM_maxLAT) RANGE [10,30]
      NUM_TEST $(GEOM_minLON) RANGE [-120,-90]
      NUM_TEST $(GEOM_minLAT) RANGE [10,30]
      NUM_TEST $(GEOM_minLON) RANGE [-120,-90]
      NUM_TEST $(GEOM_minLAT) RANGE [10,30]
      NUM_TEST $(GEOM_maxLON) RANGE [-120,-90]",<pass>
    <pass> -> FeatureReader_10 [INITIATOR]
FeatureReader_10
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_46
    ATTR_TABLE = SET_TO dataset_loc = FME_CONDITIONAL:DEFAULT_VALUE'fme://fme-server/10n090w_20101117_gmted_dsc075.tif?id=FME_SHAREDRESOURCE_DATA%2Ffilesys%2FHGDE%2FDEM%2FN10%2F10n090w_20101117_gmted_dsc075.tif&module=fmeserver&webservice=FME%20Server&connection=geopol'BOOL_OP;OR;COMPOSITE_TEST;1;TEST $(SERVER_MODE) = NO'$(FME_MF_DIR_ENCODED)DEM\N10\10n090w_20101117_gmted_dsc075.tif'FME_NUM_CONDITIONS2___
    -> N10W90
N10W90: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [10,30]
      NUM_TEST $(GEOM_maxLON) RANGE [-90,-60]
      NUM_TEST $(GEOM_maxLAT) RANGE [10,30]
      NUM_TEST $(GEOM_minLON) RANGE [-90,-60]
      NUM_TEST $(GEOM_minLAT) RANGE [10,30]
      NUM_TEST $(GEOM_minLON) RANGE [-90,-60]
      NUM_TEST $(GEOM_minLAT) RANGE [10,30]
      NUM_TEST $(GEOM_maxLON) RANGE [-90,-60]",<pass>
    <pass> -> FeatureReader_9 [INITIATOR]
FeatureReader_9
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_47
    ATTR_TABLE = SET_TO dataset_loc = FME_CONDITIONAL:DEFAULT_VALUE'fme://fme-server/10n060w_20101117_gmted_dsc075.tif?id=FME_SHAREDRESOURCE_DATA%2Ffilesys%2FHGDE%2FDEM%2FN10%2F10n060w_20101117_gmted_dsc075.tif&module=fmeserver&webservice=FME%20Server&connection=geopol'BOOL_OP;OR;COMPOSITE_TEST;1;TEST $(SERVER_MODE) = NO'$(FME_MF_DIR_ENCODED)DEM\N10\10n060w_20101117_gmted_dsc075.tif'FME_NUM_CONDITIONS2___
    -> N10W60
N10W60: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [10,30]
      NUM_TEST $(GEOM_maxLON) RANGE [-60,-30]
      NUM_TEST $(GEOM_maxLAT) RANGE [10,30]
      NUM_TEST $(GEOM_minLON) RANGE [-60,-30]
      NUM_TEST $(GEOM_minLAT) RANGE [10,30]
      NUM_TEST $(GEOM_minLON) RANGE [-60,-30]
      NUM_TEST $(GEOM_minLAT) RANGE [10,30]
      NUM_TEST $(GEOM_maxLON) RANGE [-60,-30]",<pass>
    <pass> -> FeatureReader_8 [INITIATOR]
FeatureReader_8
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_48
    ATTR_TABLE = SET_TO dataset_loc = FME_CONDITIONAL:DEFAULT_VALUE'fme://fme-server/10n030w_20101117_gmted_dsc075.tif?id=FME_SHAREDRESOURCE_DATA%2Ffilesys%2FHGDE%2FDEM%2FN10%2F10n030w_20101117_gmted_dsc075.tif&module=fmeserver&webservice=FME%20Server&connection=geopol'BOOL_OP;OR;COMPOSITE_TEST;1;TEST $(SERVER_MODE) = NO'$(FME_MF_DIR_ENCODED)DEM\N10\10n030w_20101117_gmted_dsc075.tif'FME_NUM_CONDITIONS2___
    -> N10W30
N10W30: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [10,30]
      NUM_TEST $(GEOM_maxLON) RANGE [-30,0]
      NUM_TEST $(GEOM_maxLAT) RANGE [10,30]
      NUM_TEST $(GEOM_minLON) RANGE [-30,0]
      NUM_TEST $(GEOM_minLAT) RANGE [10,30]
      NUM_TEST $(GEOM_minLON) RANGE [-30,0]
      NUM_TEST $(GEOM_minLAT) RANGE [10,30]
      NUM_TEST $(GEOM_maxLON) RANGE [-30,0]",<pass>
    <pass> -> FeatureReader_3 [INITIATOR]
FeatureReader_3
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_49
    ATTR_TABLE = SET_TO dataset_loc = FME_CONDITIONAL:DEFAULT_VALUE'fme://fme-server/10s000e_20101117_gmted_dsc075.tif?id=FME_SHAREDRESOURCE_DATA%2Ffilesys%2FHGDE%2FDEM%2FS10%2F10s000e_20101117_gmted_dsc075.tif&module=fmeserver&webservice=FME%20Server&connection=geopol'BOOL_OP;OR;COMPOSITE_TEST;1;TEST $(SERVER_MODE) = NO'$(FME_MF_DIR_ENCODED)DEM\S10\10s000e_20101117_gmted_dsc075.tif'FME_NUM_CONDITIONS2___
    -> S10E0
S10E0: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-10,10]
      NUM_TEST $(GEOM_maxLON) RANGE [0,30]
      NUM_TEST $(GEOM_maxLAT) RANGE [-10,10]
      NUM_TEST $(GEOM_minLON) RANGE [0,30]
      NUM_TEST $(GEOM_minLAT) RANGE [-10,10]
      NUM_TEST $(GEOM_minLON) RANGE [0,30]
      NUM_TEST $(GEOM_minLAT) RANGE [-10,10]
      NUM_TEST $(GEOM_maxLON) RANGE [0,30]",<pass>
    <pass> -> FeatureReader_50 [INITIATOR]
FeatureReader_50
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_50
    ATTR_TABLE = SET_TO dataset_loc = FME_CONDITIONAL:DEFAULT_VALUE'fme://fme-server/10s030e_20101117_gmted_dsc075.tif?id=FME_SHAREDRESOURCE_DATA%2Ffilesys%2FHGDE%2FDEM%2FS10%2F10s030e_20101117_gmted_dsc075.tif&module=fmeserver&webservice=FME%20Server&connection=geopol'BOOL_OP;OR;COMPOSITE_TEST;1;TEST $(SERVER_MODE) = NO'$(FME_MF_DIR_ENCODED)DEM\S10\10s030e_20101117_gmted_dsc075.tif'FME_NUM_CONDITIONS2___
    -> S10E30
S10E30: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-10,10]
      NUM_TEST $(GEOM_maxLON) RANGE [30,60]
      NUM_TEST $(GEOM_maxLAT) RANGE [-10,10]
      NUM_TEST $(GEOM_minLON) RANGE [30,60]
      NUM_TEST $(GEOM_minLAT) RANGE [-10,10]
      NUM_TEST $(GEOM_minLON) RANGE [30,60]
      NUM_TEST $(GEOM_minLAT) RANGE [-10,10]
      NUM_TEST $(GEOM_maxLON) RANGE [30,60]",<pass>
    <pass> -> FeatureReader_49 [INITIATOR]
FeatureReader_49
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_51
    ATTR_TABLE = SET_TO dataset_loc = FME_CONDITIONAL:DEFAULT_VALUE'fme://fme-server/10s060e_20101117_gmted_dsc075.tif?id=FME_SHAREDRESOURCE_DATA%2Ffilesys%2FHGDE%2FDEM%2FS10%2F10s060e_20101117_gmted_dsc075.tif&module=fmeserver&webservice=FME%20Server&connection=geopol'BOOL_OP;OR;COMPOSITE_TEST;1;TEST $(SERVER_MODE) = NO'$(FME_MF_DIR_ENCODED)DEM\S10\10s060e_20101117_gmted_dsc075.tif'FME_NUM_CONDITIONS2___
    -> S10E60
S10E60: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-10,10]
      NUM_TEST $(GEOM_maxLON) RANGE [60,90]
      NUM_TEST $(GEOM_maxLAT) RANGE [-10,10]
      NUM_TEST $(GEOM_minLON) RANGE [60,90]
      NUM_TEST $(GEOM_minLAT) RANGE [-10,10]
      NUM_TEST $(GEOM_minLON) RANGE [60,90]
      NUM_TEST $(GEOM_minLAT) RANGE [-10,10]
      NUM_TEST $(GEOM_maxLON) RANGE [60,90]",<pass>
    <pass> -> FeatureReader_52 [INITIATOR]
FeatureReader_52
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_52
    ATTR_TABLE = SET_TO dataset_loc = FME_CONDITIONAL:DEFAULT_VALUE'fme://fme-server/10s090e_20101117_gmted_dsc075.tif?id=FME_SHAREDRESOURCE_DATA%2Ffilesys%2FHGDE%2FDEM%2FS10%2F10s090e_20101117_gmted_dsc075.tif&module=fmeserver&webservice=FME%20Server&connection=geopol'BOOL_OP;OR;COMPOSITE_TEST;1;TEST $(SERVER_MODE) = NO'$(FME_MF_DIR_ENCODED)DEM\S10\10s090e_20101117_gmted_dsc075.tif'FME_NUM_CONDITIONS2___
    -> S10E90
S10E90: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-10,10]
      NUM_TEST $(GEOM_maxLON) RANGE [90,120]
      NUM_TEST $(GEOM_maxLAT) RANGE [-10,10]
      NUM_TEST $(GEOM_minLON) RANGE [90,120]
      NUM_TEST $(GEOM_minLAT) RANGE [-10,10]
      NUM_TEST $(GEOM_minLON) RANGE [90,120]
      NUM_TEST $(GEOM_minLAT) RANGE [-10,10]
      NUM_TEST $(GEOM_maxLON) RANGE [90,120]",<pass>
    <pass> -> FeatureReader_53 [INITIATOR]
FeatureReader_53
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_53
    ATTR_TABLE = SET_TO dataset_loc = FME_CONDITIONAL:DEFAULT_VALUE'fme://fme-server/10s120e_20101117_gmted_dsc075.tif?id=FME_SHAREDRESOURCE_DATA%2Ffilesys%2FHGDE%2FDEM%2FS10%2F10s120e_20101117_gmted_dsc075.tif&module=fmeserver&webservice=FME%20Server&connection=geopol'BOOL_OP;OR;COMPOSITE_TEST;1;TEST $(SERVER_MODE) = NO'$(FME_MF_DIR_ENCODED)DEM\S10\10s120e_20101117_gmted_dsc075.tif'FME_NUM_CONDITIONS2___
    -> S10E120
S10E120: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-10,10]
      NUM_TEST $(GEOM_maxLON) RANGE [120,150]
      NUM_TEST $(GEOM_maxLAT) RANGE [-10,10]
      NUM_TEST $(GEOM_minLON) RANGE [120,150]
      NUM_TEST $(GEOM_minLAT) RANGE [-10,10]
      NUM_TEST $(GEOM_minLON) RANGE [120,150]
      NUM_TEST $(GEOM_minLAT) RANGE [-10,10]
      NUM_TEST $(GEOM_maxLON) RANGE [120,150]",<pass>
    <pass> -> FeatureReader_54 [INITIATOR]
FeatureReader_54
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_54
    ATTR_TABLE = SET_TO dataset_loc = FME_CONDITIONAL:DEFAULT_VALUE'fme://fme-server/10s150e_20101117_gmted_dsc075.tif?id=FME_SHAREDRESOURCE_DATA%2Ffilesys%2FHGDE%2FDEM%2FS10%2F10s150e_20101117_gmted_dsc075.tif&module=fmeserver&webservice=FME%20Server&connection=geopol'BOOL_OP;OR;COMPOSITE_TEST;1;TEST $(SERVER_MODE) = NO'$(FME_MF_DIR_ENCODED)DEM\S10\10s150e_20101117_gmted_dsc075.tif'FME_NUM_CONDITIONS2___
    -> S10E150
S10E150: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-10,10]
      NUM_TEST $(GEOM_maxLON) RANGE [150,180]
      NUM_TEST $(GEOM_maxLAT) RANGE [-10,10]
      NUM_TEST $(GEOM_minLON) RANGE [150,180]
      NUM_TEST $(GEOM_minLAT) RANGE [-10,10]
      NUM_TEST $(GEOM_minLON) RANGE [150,180]
      NUM_TEST $(GEOM_minLAT) RANGE [-10,10]
      NUM_TEST $(GEOM_maxLON) RANGE [150,180]",<pass>
    <pass> -> FeatureReader_55 [INITIATOR]
FeatureReader_55
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_55
    ATTR_TABLE = SET_TO dataset_loc = FME_CONDITIONAL:DEFAULT_VALUE'fme://fme-server/10s030w_20101117_gmted_dsc075.tif?id=FME_SHAREDRESOURCE_DATA%2Ffilesys%2FHGDE%2FDEM%2FS10%2F10s030w_20101117_gmted_dsc075.tif&module=fmeserver&webservice=FME%20Server&connection=geopol'BOOL_OP;OR;COMPOSITE_TEST;1;TEST $(SERVER_MODE) = NO'$(FME_MF_DIR_ENCODED)DEM\S10\10s030w_20101117_gmted_dsc075.tif'FME_NUM_CONDITIONS2___
    -> S10W30
S10W30: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-10,10]
      NUM_TEST $(GEOM_maxLON) RANGE [-30,0]
      NUM_TEST $(GEOM_maxLAT) RANGE [-10,10]
      NUM_TEST $(GEOM_minLON) RANGE [-30,0]
      NUM_TEST $(GEOM_minLAT) RANGE [-10,10]
      NUM_TEST $(GEOM_minLON) RANGE [-30,0]
      NUM_TEST $(GEOM_minLAT) RANGE [-10,10]
      NUM_TEST $(GEOM_maxLON) RANGE [-30,0]",<pass>
    <pass> -> FeatureReader_51 [INITIATOR]
FeatureReader_51
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_56
    ATTR_TABLE = SET_TO dataset_loc = FME_CONDITIONAL:DEFAULT_VALUE'fme://fme-server/10s060w_20101117_gmted_dsc075.tif?id=FME_SHAREDRESOURCE_DATA%2Ffilesys%2FHGDE%2FDEM%2FS10%2F10s060w_20101117_gmted_dsc075.tif&module=fmeserver&webservice=FME%20Server&connection=geopol'BOOL_OP;OR;COMPOSITE_TEST;1;TEST $(SERVER_MODE) = NO'$(FME_MF_DIR_ENCODED)DEM\S10\10s060w_20101117_gmted_dsc075.tif'FME_NUM_CONDITIONS2___
    -> S10W60
S10W60: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-10,10]
      NUM_TEST $(GEOM_maxLON) RANGE [-60,-30]
      NUM_TEST $(GEOM_maxLAT) RANGE [-10,10]
      NUM_TEST $(GEOM_minLON) RANGE [-60,-30]
      NUM_TEST $(GEOM_minLAT) RANGE [-10,10]
      NUM_TEST $(GEOM_minLON) RANGE [-60,-30]
      NUM_TEST $(GEOM_minLAT) RANGE [-10,10]
      NUM_TEST $(GEOM_maxLON) RANGE [-60,-30]",<pass>
    <pass> -> FeatureReader_56 [INITIATOR]
FeatureReader_56
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_57
    ATTR_TABLE = SET_TO dataset_loc = FME_CONDITIONAL:DEFAULT_VALUE'fme://fme-server/10s090w_20101117_gmted_dsc075.tif?id=FME_SHAREDRESOURCE_DATA%2Ffilesys%2FHGDE%2FDEM%2FS10%2F10s090w_20101117_gmted_dsc075.tif&module=fmeserver&webservice=FME%20Server&connection=geopol'BOOL_OP;OR;COMPOSITE_TEST;1;TEST $(SERVER_MODE) = NO'$(FME_MF_DIR_ENCODED)DEM\S10\10s090w_20101117_gmted_dsc075.tif'FME_NUM_CONDITIONS2___
    -> S10W90
S10W90: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-10,10]
      NUM_TEST $(GEOM_maxLON) RANGE [-90,-60]
      NUM_TEST $(GEOM_maxLAT) RANGE [-10,10]
      NUM_TEST $(GEOM_minLON) RANGE [-90,-60]
      NUM_TEST $(GEOM_minLAT) RANGE [-10,10]
      NUM_TEST $(GEOM_minLON) RANGE [-90,-60]
      NUM_TEST $(GEOM_minLAT) RANGE [-10,10]
      NUM_TEST $(GEOM_maxLON) RANGE [-90,-60]",<pass>
    <pass> -> FeatureReader_57 [INITIATOR]
FeatureReader_57
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_58
    ATTR_TABLE = SET_TO dataset_loc = FME_CONDITIONAL:DEFAULT_VALUE'fme://fme-server/10s120w_20101117_gmted_dsc075.tif?id=FME_SHAREDRESOURCE_DATA%2Ffilesys%2FHGDE%2FDEM%2FS10%2F10s120w_20101117_gmted_dsc075.tif&module=fmeserver&webservice=FME%20Server&connection=geopol'BOOL_OP;OR;COMPOSITE_TEST;1;TEST $(SERVER_MODE) = NO'$(FME_MF_DIR_ENCODED)DEM\S10\10s120w_20101117_gmted_dsc075.tif'FME_NUM_CONDITIONS2___
    -> S10W120
S10W120: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-10,10]
      NUM_TEST $(GEOM_maxLON) RANGE [-120,-90]
      NUM_TEST $(GEOM_maxLAT) RANGE [-10,10]
      NUM_TEST $(GEOM_minLON) RANGE [-120,-90]
      NUM_TEST $(GEOM_minLAT) RANGE [-10,10]
      NUM_TEST $(GEOM_minLON) RANGE [-120,-90]
      NUM_TEST $(GEOM_minLAT) RANGE [-10,10]
      NUM_TEST $(GEOM_maxLON) RANGE [-120,-90]",<pass>
    <pass> -> FeatureReader_58 [INITIATOR]
FeatureReader_58
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_59
    ATTR_TABLE = SET_TO dataset_loc = FME_CONDITIONAL:DEFAULT_VALUE'fme://fme-server/10s150w_20101117_gmted_dsc075.tif?id=FME_SHAREDRESOURCE_DATA%2Ffilesys%2FHGDE%2FDEM%2FS10%2F10s150w_20101117_gmted_dsc075.tif&module=fmeserver&webservice=FME%20Server&connection=geopol'BOOL_OP;OR;COMPOSITE_TEST;1;TEST $(SERVER_MODE) = NO'$(FME_MF_DIR_ENCODED)DEM\S10\10s150w_20101117_gmted_dsc075.tif'FME_NUM_CONDITIONS2___
    -> S10W150
S10W150: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-10,10]
      NUM_TEST $(GEOM_maxLON) RANGE [-150,-120]
      NUM_TEST $(GEOM_maxLAT) RANGE [-10,10]
      NUM_TEST $(GEOM_minLON) RANGE [-150,-120]
      NUM_TEST $(GEOM_minLAT) RANGE [-10,10]
      NUM_TEST $(GEOM_minLON) RANGE [-150,-120]
      NUM_TEST $(GEOM_minLAT) RANGE [-10,10]
      NUM_TEST $(GEOM_maxLON) RANGE [-150,-120]",<pass>
    <pass> -> FeatureReader_59 [INITIATOR]
FeatureReader_59
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_60
    ATTR_TABLE = SET_TO dataset_loc = FME_CONDITIONAL:DEFAULT_VALUE'fme://fme-server/10s180w_20101117_gmted_dsc075.tif?id=FME_SHAREDRESOURCE_DATA%2Ffilesys%2FHGDE%2FDEM%2FS10%2F10s180w_20101117_gmted_dsc075.tif&module=fmeserver&webservice=FME%20Server&connection=geopol'BOOL_OP;OR;COMPOSITE_TEST;1;TEST $(SERVER_MODE) = NO'$(FME_MF_DIR_ENCODED)DEM\S10\10s180w_20101117_gmted_dsc075.tif'FME_NUM_CONDITIONS2___
    -> S10W180
S10W180: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-10,10]
      NUM_TEST $(GEOM_maxLON) RANGE [-180,-150]
      NUM_TEST $(GEOM_maxLAT) RANGE [-10,10]
      NUM_TEST $(GEOM_minLON) RANGE [-180,-150]
      NUM_TEST $(GEOM_minLAT) RANGE [-10,10]
      NUM_TEST $(GEOM_minLON) RANGE [-180,-150]
      NUM_TEST $(GEOM_minLAT) RANGE [-10,10]
      NUM_TEST $(GEOM_maxLON) RANGE [-180,-150]",<pass>
    <pass> -> FeatureReader_60 [INITIATOR]
FeatureReader_60
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_61
    ATTR_TABLE = SET_TO dataset_loc = FME_CONDITIONAL:DEFAULT_VALUE'fme://fme-server/30s000e_20101117_gmted_dsc075.tif?id=FME_SHAREDRESOURCE_DATA%2Ffilesys%2FHGDE%2FDEM%2FS30%2F30s000e_20101117_gmted_dsc075.tif&module=fmeserver&webservice=FME%20Server&connection=geopol'BOOL_OP;OR;COMPOSITE_TEST;1;TEST $(SERVER_MODE) = NO'$(FME_MF_DIR_ENCODED)DEM\S30\30s000e_20101117_gmted_dsc075.tif'FME_NUM_CONDITIONS2___
    -> S30E0
S30E0: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-30,-10]
      NUM_TEST $(GEOM_maxLON) RANGE [0,30]
      NUM_TEST $(GEOM_maxLAT) RANGE [-30,-10]
      NUM_TEST $(GEOM_minLON) RANGE [0,30]
      NUM_TEST $(GEOM_minLAT) RANGE [-30,-10]
      NUM_TEST $(GEOM_minLON) RANGE [0,30]
      NUM_TEST $(GEOM_minLAT) RANGE [-30,-10]
      NUM_TEST $(GEOM_maxLON) RANGE [0,30]",<pass>
    <pass> -> FeatureReader_62 [INITIATOR]
FeatureReader_62
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_62
    ATTR_TABLE = SET_TO dataset_loc = FME_CONDITIONAL:DEFAULT_VALUE'fme://fme-server/30s030e_20101117_gmted_dsc075.tif?id=FME_SHAREDRESOURCE_DATA%2Ffilesys%2FHGDE%2FDEM%2FS30%2F30s030e_20101117_gmted_dsc075.tif&module=fmeserver&webservice=FME%20Server&connection=geopol'BOOL_OP;OR;COMPOSITE_TEST;1;TEST $(SERVER_MODE) = NO'$(FME_MF_DIR_ENCODED)DEM\S30\30s030e_20101117_gmted_dsc075.tif'FME_NUM_CONDITIONS2___
    -> S30E30
S30E30: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-30,-10]
      NUM_TEST $(GEOM_maxLON) RANGE [30,60]
      NUM_TEST $(GEOM_maxLAT) RANGE [-30,-10]
      NUM_TEST $(GEOM_minLON) RANGE [30,60]
      NUM_TEST $(GEOM_minLAT) RANGE [-30,-10]
      NUM_TEST $(GEOM_minLON) RANGE [30,60]
      NUM_TEST $(GEOM_minLAT) RANGE [-30,-10]
      NUM_TEST $(GEOM_maxLON) RANGE [30,60]",<pass>
    <pass> -> FeatureReader_61 [INITIATOR]
FeatureReader_61
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_63
    ATTR_TABLE = SET_TO dataset_loc = FME_CONDITIONAL:DEFAULT_VALUE'fme://fme-server/30s060e_20101117_gmted_dsc075.tif?id=FME_SHAREDRESOURCE_DATA%2Ffilesys%2FHGDE%2FDEM%2FS30%2F30s060e_20101117_gmted_dsc075.tif&module=fmeserver&webservice=FME%20Server&connection=geopol'BOOL_OP;OR;COMPOSITE_TEST;1;TEST $(SERVER_MODE) = NO'$(FME_MF_DIR_ENCODED)DEM\S30\30s060e_20101117_gmted_dsc075.tif'FME_NUM_CONDITIONS2___
    -> S30E60
S30E60: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-30,-10]
      NUM_TEST $(GEOM_maxLON) RANGE [60,90]
      NUM_TEST $(GEOM_maxLAT) RANGE [-30,-10]
      NUM_TEST $(GEOM_minLON) RANGE [60,90]
      NUM_TEST $(GEOM_minLAT) RANGE [-30,-10]
      NUM_TEST $(GEOM_minLON) RANGE [60,90]
      NUM_TEST $(GEOM_minLAT) RANGE [-30,-10]
      NUM_TEST $(GEOM_maxLON) RANGE [60,90]",<pass>
    <pass> -> FeatureReader_64 [INITIATOR]
FeatureReader_64
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_64
    ATTR_TABLE = SET_TO dataset_loc = FME_CONDITIONAL:DEFAULT_VALUE'fme://fme-server/30s090e_20101117_gmted_dsc075.tif?id=FME_SHAREDRESOURCE_DATA%2Ffilesys%2FHGDE%2FDEM%2FS30%2F30s090e_20101117_gmted_dsc075.tif&module=fmeserver&webservice=FME%20Server&connection=geopol'BOOL_OP;OR;COMPOSITE_TEST;1;TEST $(SERVER_MODE) = NO'$(FME_MF_DIR_ENCODED)DEM\S30\30s090e_20101117_gmted_dsc075.tif'FME_NUM_CONDITIONS2___
    -> S30E90
S30E90: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-30,-10]
      NUM_TEST $(GEOM_maxLON) RANGE [90,120]
      NUM_TEST $(GEOM_maxLAT) RANGE [-30,-10]
      NUM_TEST $(GEOM_minLON) RANGE [90,120]
      NUM_TEST $(GEOM_minLAT) RANGE [-30,-10]
      NUM_TEST $(GEOM_minLON) RANGE [90,120]
      NUM_TEST $(GEOM_minLAT) RANGE [-30,-10]
      NUM_TEST $(GEOM_maxLON) RANGE [90,120]",<pass>
    <pass> -> FeatureReader_65 [INITIATOR]
FeatureReader_65
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_65
    ATTR_TABLE = SET_TO dataset_loc = FME_CONDITIONAL:DEFAULT_VALUE'fme://fme-server/30s120e_20101117_gmted_dsc075.tif?id=FME_SHAREDRESOURCE_DATA%2Ffilesys%2FHGDE%2FDEM%2FS30%2F30s120e_20101117_gmted_dsc075.tif&module=fmeserver&webservice=FME%20Server&connection=geopol'BOOL_OP;OR;COMPOSITE_TEST;1;TEST $(SERVER_MODE) = NO'$(FME_MF_DIR_ENCODED)DEM\S30\30s120e_20101117_gmted_dsc075.tif'FME_NUM_CONDITIONS2___
    -> S30E120
S30E120: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-30,-10]
      NUM_TEST $(GEOM_maxLON) RANGE [120,150]
      NUM_TEST $(GEOM_maxLAT) RANGE [-30,-10]
      NUM_TEST $(GEOM_minLON) RANGE [120,150]
      NUM_TEST $(GEOM_minLAT) RANGE [-30,-10]
      NUM_TEST $(GEOM_minLON) RANGE [120,150]
      NUM_TEST $(GEOM_minLAT) RANGE [-30,-10]
      NUM_TEST $(GEOM_maxLON) RANGE [120,150]",<pass>
    <pass> -> FeatureReader_66 [INITIATOR]
FeatureReader_66
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_66
    ATTR_TABLE = SET_TO dataset_loc = FME_CONDITIONAL:DEFAULT_VALUE'fme://fme-server/30s150e_20101117_gmted_dsc075.tif?id=FME_SHAREDRESOURCE_DATA%2Ffilesys%2FHGDE%2FDEM%2FS30%2F30s150e_20101117_gmted_dsc075.tif&module=fmeserver&webservice=FME%20Server&connection=geopol'BOOL_OP;OR;COMPOSITE_TEST;1;TEST $(SERVER_MODE) = NO'$(FME_MF_DIR_ENCODED)DEM\S30\30s150e_20101117_gmted_dsc075.tif'FME_NUM_CONDITIONS2___
    -> S30E150
S30E150: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-30,-10]
      NUM_TEST $(GEOM_maxLON) RANGE [150,180]
      NUM_TEST $(GEOM_maxLAT) RANGE [-30,-10]
      NUM_TEST $(GEOM_minLON) RANGE [150,180]
      NUM_TEST $(GEOM_minLAT) RANGE [-30,-10]
      NUM_TEST $(GEOM_minLON) RANGE [150,180]
      NUM_TEST $(GEOM_minLAT) RANGE [-30,-10]
      NUM_TEST $(GEOM_maxLON) RANGE [150,180]",<pass>
    <pass> -> FeatureReader_67 [INITIATOR]
FeatureReader_67
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_67
    ATTR_TABLE = SET_TO dataset_loc = FME_CONDITIONAL:DEFAULT_VALUE'fme://fme-server/30s030w_20101117_gmted_dsc075.tif?id=FME_SHAREDRESOURCE_DATA%2Ffilesys%2FHGDE%2FDEM%2FS30%2F30s030w_20101117_gmted_dsc075.tif&module=fmeserver&webservice=FME%20Server&connection=geopol'BOOL_OP;OR;COMPOSITE_TEST;1;TEST $(SERVER_MODE) = NO'$(FME_MF_DIR_ENCODED)DEM\S30\30s030w_20101117_gmted_dsc075.tif'FME_NUM_CONDITIONS2___
    -> S30W30
S30W30: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-30,-10]
      NUM_TEST $(GEOM_maxLON) RANGE [-30,0]
      NUM_TEST $(GEOM_maxLAT) RANGE [-30,-10]
      NUM_TEST $(GEOM_minLON) RANGE [-30,0]
      NUM_TEST $(GEOM_minLAT) RANGE [-30,-10]
      NUM_TEST $(GEOM_minLON) RANGE [-30,0]
      NUM_TEST $(GEOM_minLAT) RANGE [-30,-10]
      NUM_TEST $(GEOM_maxLON) RANGE [-30,0]",<pass>
    <pass> -> FeatureReader_63 [INITIATOR]
FeatureReader_63
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_68
    ATTR_TABLE = SET_TO dataset_loc = FME_CONDITIONAL:DEFAULT_VALUE'fme://fme-server/30s060w_20101117_gmted_dsc075.tif?id=FME_SHAREDRESOURCE_DATA%2Ffilesys%2FHGDE%2FDEM%2FS30%2F30s060w_20101117_gmted_dsc075.tif&module=fmeserver&webservice=FME%20Server&connection=geopol'BOOL_OP;OR;COMPOSITE_TEST;1;TEST $(SERVER_MODE) = NO'$(FME_MF_DIR_ENCODED)DEM\S30\30s060w_20101117_gmted_dsc075.tif'FME_NUM_CONDITIONS2___
    -> S30W60
S30W60: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-30,-10]
      NUM_TEST $(GEOM_maxLON) RANGE [-60,-30]
      NUM_TEST $(GEOM_maxLAT) RANGE [-30,-10]
      NUM_TEST $(GEOM_minLON) RANGE [-60,-30]
      NUM_TEST $(GEOM_minLAT) RANGE [-30,-10]
      NUM_TEST $(GEOM_minLON) RANGE [-60,-30]
      NUM_TEST $(GEOM_minLAT) RANGE [-30,-10]
      NUM_TEST $(GEOM_maxLON) RANGE [-60,-30]",<pass>
    <pass> -> FeatureReader_68 [INITIATOR]
FeatureReader_68
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_69
    ATTR_TABLE = SET_TO dataset_loc = FME_CONDITIONAL:DEFAULT_VALUE'fme://fme-server/30s090w_20101117_gmted_dsc075.tif?id=FME_SHAREDRESOURCE_DATA%2Ffilesys%2FHGDE%2FDEM%2FS30%2F30s090w_20101117_gmted_dsc075.tif&module=fmeserver&webservice=FME%20Server&connection=geopol'BOOL_OP;OR;COMPOSITE_TEST;1;TEST $(SERVER_MODE) = NO'$(FME_MF_DIR_ENCODED)DEM\S30\30s090w_20101117_gmted_dsc075.tif'FME_NUM_CONDITIONS2___
    -> S30W90
S30W90: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-30,-10]
      NUM_TEST $(GEOM_maxLON) RANGE [-90,-60]
      NUM_TEST $(GEOM_maxLAT) RANGE [-30,-10]
      NUM_TEST $(GEOM_minLON) RANGE [-90,-60]
      NUM_TEST $(GEOM_minLAT) RANGE [-30,-10]
      NUM_TEST $(GEOM_minLON) RANGE [-90,-60]
      NUM_TEST $(GEOM_minLAT) RANGE [-30,-10]
      NUM_TEST $(GEOM_maxLON) RANGE [-90,-60]",<pass>
    <pass> -> FeatureReader_69 [INITIATOR]
FeatureReader_69
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_70
    ATTR_TABLE = SET_TO dataset_loc = FME_CONDITIONAL:DEFAULT_VALUE'fme://fme-server/30s120w_20101117_gmted_dsc075.tif?id=FME_SHAREDRESOURCE_DATA%2Ffilesys%2FHGDE%2FDEM%2FS30%2F30s120w_20101117_gmted_dsc075.tif&module=fmeserver&webservice=FME%20Server&connection=geopol'BOOL_OP;OR;COMPOSITE_TEST;1;TEST $(SERVER_MODE) = NO'$(FME_MF_DIR_ENCODED)DEM\S30\30s120w_20101117_gmted_dsc075.tif'FME_NUM_CONDITIONS2___
    -> S30W120
S30W120: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-30,-10]
      NUM_TEST $(GEOM_maxLON) RANGE [-120,-90]
      NUM_TEST $(GEOM_maxLAT) RANGE [-30,-10]
      NUM_TEST $(GEOM_minLON) RANGE [-120,-90]
      NUM_TEST $(GEOM_minLAT) RANGE [-30,-10]
      NUM_TEST $(GEOM_minLON) RANGE [-120,-90]
      NUM_TEST $(GEOM_minLAT) RANGE [-30,-10]
      NUM_TEST $(GEOM_maxLON) RANGE [-120,-90]",<pass>
    <pass> -> FeatureReader_70 [INITIATOR]
FeatureReader_70
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_71
    ATTR_TABLE = SET_TO dataset_loc = FME_CONDITIONAL:DEFAULT_VALUE'fme://fme-server/30s150w_20101117_gmted_dsc075.tif?id=FME_SHAREDRESOURCE_DATA%2Ffilesys%2FHGDE%2FDEM%2FS30%2F30s150w_20101117_gmted_dsc075.tif&module=fmeserver&webservice=FME%20Server&connection=geopol'BOOL_OP;OR;COMPOSITE_TEST;1;TEST $(SERVER_MODE) = NO'$(FME_MF_DIR_ENCODED)DEM\S30\30s150w_20101117_gmted_dsc075.tif'FME_NUM_CONDITIONS2___
    -> S30W150
S30W150: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-30,-10]
      NUM_TEST $(GEOM_maxLON) RANGE [-150,-120]
      NUM_TEST $(GEOM_maxLAT) RANGE [-30,-10]
      NUM_TEST $(GEOM_minLON) RANGE [-150,-120]
      NUM_TEST $(GEOM_minLAT) RANGE [-30,-10]
      NUM_TEST $(GEOM_minLON) RANGE [-150,-120]
      NUM_TEST $(GEOM_minLAT) RANGE [-30,-10]
      NUM_TEST $(GEOM_maxLON) RANGE [-150,-120]",<pass>
    <pass> -> FeatureReader_71 [INITIATOR]
FeatureReader_71
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_72
    ATTR_TABLE = SET_TO dataset_loc = FME_CONDITIONAL:DEFAULT_VALUE'fme://fme-server/30s180w_20101117_gmted_dsc075.tif?id=FME_SHAREDRESOURCE_DATA%2Ffilesys%2FHGDE%2FDEM%2FS30%2F30s180w_20101117_gmted_dsc075.tif&module=fmeserver&webservice=FME%20Server&connection=geopol'BOOL_OP;OR;COMPOSITE_TEST;1;TEST $(SERVER_MODE) = NO'$(FME_MF_DIR_ENCODED)DEM\S30\30s180w_20101117_gmted_dsc075.tif'FME_NUM_CONDITIONS2___
    -> S30W180
S30W180: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-30,-10]
      NUM_TEST $(GEOM_maxLON) RANGE [-180,-150]
      NUM_TEST $(GEOM_maxLAT) RANGE [-30,-10]
      NUM_TEST $(GEOM_minLON) RANGE [-180,-150]
      NUM_TEST $(GEOM_minLAT) RANGE [-30,-10]
      NUM_TEST $(GEOM_minLON) RANGE [-180,-150]
      NUM_TEST $(GEOM_minLAT) RANGE [-30,-10]
      NUM_TEST $(GEOM_maxLON) RANGE [-180,-150]",<pass>
    <pass> -> FeatureReader_72 [INITIATOR]
FeatureReader_72
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_73
    ATTR_TABLE = SET_TO dataset_loc = FME_CONDITIONAL:DEFAULT_VALUE'fme://fme-server/50s000e_20101117_gmted_dsc075.tif?id=FME_SHAREDRESOURCE_DATA%2Ffilesys%2FHGDE%2FDEM%2FS50%2F50s000e_20101117_gmted_dsc075.tif&module=fmeserver&webservice=FME%20Server&connection=geopol'BOOL_OP;OR;COMPOSITE_TEST;1;TEST $(SERVER_MODE) = NO'$(FME_MF_DIR_ENCODED)DEM\S50\50s000e_20101117_gmted_dsc075.tif'FME_NUM_CONDITIONS2___
    -> S50E0
S50E0: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-50,-30]
      NUM_TEST $(GEOM_maxLON) RANGE [0,30]
      NUM_TEST $(GEOM_maxLAT) RANGE [-50,-30]
      NUM_TEST $(GEOM_minLON) RANGE [0,30]
      NUM_TEST $(GEOM_minLAT) RANGE [-50,-30]
      NUM_TEST $(GEOM_minLON) RANGE [0,30]
      NUM_TEST $(GEOM_minLAT) RANGE [-50,-30]
      NUM_TEST $(GEOM_maxLON) RANGE [0,30]",<pass>
    <pass> -> FeatureReader_74 [INITIATOR]
FeatureReader_74
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_74
    ATTR_TABLE = SET_TO dataset_loc = FME_CONDITIONAL:DEFAULT_VALUE'fme://fme-server/50s030e_20101117_gmted_dsc075.tif?id=FME_SHAREDRESOURCE_DATA%2Ffilesys%2FHGDE%2FDEM%2FS50%2F50s030e_20101117_gmted_dsc075.tif&module=fmeserver&webservice=FME%20Server&connection=geopol'BOOL_OP;OR;COMPOSITE_TEST;1;TEST $(SERVER_MODE) = NO'$(FME_MF_DIR_ENCODED)DEM\S50\50s030e_20101117_gmted_dsc075.tif'FME_NUM_CONDITIONS2___
    -> S50E30
S50E30: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-50,-30]
      NUM_TEST $(GEOM_maxLON) RANGE [30,60]
      NUM_TEST $(GEOM_maxLAT) RANGE [-50,-30]
      NUM_TEST $(GEOM_minLON) RANGE [30,60]
      NUM_TEST $(GEOM_minLAT) RANGE [-50,-30]
      NUM_TEST $(GEOM_minLON) RANGE [30,60]
      NUM_TEST $(GEOM_minLAT) RANGE [-50,-30]
      NUM_TEST $(GEOM_maxLON) RANGE [30,60]",<pass>
    <pass> -> FeatureReader_73 [INITIATOR]
FeatureReader_73
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_75
    ATTR_TABLE = SET_TO dataset_loc = FME_CONDITIONAL:DEFAULT_VALUE'fme://fme-server/50s060e_20101117_gmted_dsc075.tif?id=FME_SHAREDRESOURCE_DATA%2Ffilesys%2FHGDE%2FDEM%2FS50%2F50s060e_20101117_gmted_dsc075.tif&module=fmeserver&webservice=FME%20Server&connection=geopol'BOOL_OP;OR;COMPOSITE_TEST;1;TEST $(SERVER_MODE) = NO'$(FME_MF_DIR_ENCODED)DEM\S50\50s060e_20101117_gmted_dsc075.tif'FME_NUM_CONDITIONS2___
    -> S50E60
S50E60: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-50,-30]
      NUM_TEST $(GEOM_maxLON) RANGE [60,90]
      NUM_TEST $(GEOM_maxLAT) RANGE [-50,-30]
      NUM_TEST $(GEOM_minLON) RANGE [60,90]
      NUM_TEST $(GEOM_minLAT) RANGE [-50,-30]
      NUM_TEST $(GEOM_minLON) RANGE [60,90]
      NUM_TEST $(GEOM_minLAT) RANGE [-50,-30]
      NUM_TEST $(GEOM_maxLON) RANGE [60,90]",<pass>
    <pass> -> FeatureReader_76 [INITIATOR]
FeatureReader_76
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_76
    ATTR_TABLE = SET_TO dataset_loc = FME_CONDITIONAL:DEFAULT_VALUE'fme://fme-server/50s090e_20101117_gmted_dsc075.tif?id=FME_SHAREDRESOURCE_DATA%2Ffilesys%2FHGDE%2FDEM%2FS50%2F50s090e_20101117_gmted_dsc075.tif&module=fmeserver&webservice=FME%20Server&connection=geopol'BOOL_OP;OR;COMPOSITE_TEST;1;TEST $(SERVER_MODE) = NO'$(FME_MF_DIR_ENCODED)DEM\S50\50s090e_20101117_gmted_dsc075.tif'FME_NUM_CONDITIONS2___
    -> S50E90
S50E90: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-50,-30]
      NUM_TEST $(GEOM_maxLON) RANGE [90,120]
      NUM_TEST $(GEOM_maxLAT) RANGE [-50,-30]
      NUM_TEST $(GEOM_minLON) RANGE [90,120]
      NUM_TEST $(GEOM_minLAT) RANGE [-50,-30]
      NUM_TEST $(GEOM_minLON) RANGE [90,120]
      NUM_TEST $(GEOM_minLAT) RANGE [-50,-30]
      NUM_TEST $(GEOM_maxLON) RANGE [90,120]",<pass>
    <pass> -> FeatureReader_77 [INITIATOR]
FeatureReader_77
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_77
    ATTR_TABLE = SET_TO dataset_loc = FME_CONDITIONAL:DEFAULT_VALUE'fme://fme-server/50s120e_20101117_gmted_dsc075.tif?id=FME_SHAREDRESOURCE_DATA%2Ffilesys%2FHGDE%2FDEM%2FS50%2F50s120e_20101117_gmted_dsc075.tif&module=fmeserver&webservice=FME%20Server&connection=geopol'BOOL_OP;OR;COMPOSITE_TEST;1;TEST $(SERVER_MODE) = NO'$(FME_MF_DIR_ENCODED)DEM\S50\50s120e_20101117_gmted_dsc075.tif'FME_NUM_CONDITIONS2___
    -> S50E120
S50E120: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-50,-30]
      NUM_TEST $(GEOM_maxLON) RANGE [120,150]
      NUM_TEST $(GEOM_maxLAT) RANGE [-50,-30]
      NUM_TEST $(GEOM_minLON) RANGE [120,150]
      NUM_TEST $(GEOM_minLAT) RANGE [-50,-30]
      NUM_TEST $(GEOM_minLON) RANGE [120,150]
      NUM_TEST $(GEOM_minLAT) RANGE [-50,-30]
      NUM_TEST $(GEOM_maxLON) RANGE [120,150]",<pass>
    <pass> -> FeatureReader_78 [INITIATOR]
FeatureReader_78
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_78
    ATTR_TABLE = SET_TO dataset_loc = FME_CONDITIONAL:DEFAULT_VALUE'fme://fme-server/50s150e_20101117_gmted_dsc075.tif?id=FME_SHAREDRESOURCE_DATA%2Ffilesys%2FHGDE%2FDEM%2FS50%2F50s150e_20101117_gmted_dsc075.tif&module=fmeserver&webservice=FME%20Server&connection=geopol'BOOL_OP;OR;COMPOSITE_TEST;1;TEST $(SERVER_MODE) = NO'$(FME_MF_DIR_ENCODED)DEM\S50\50s150e_20101117_gmted_dsc075.tif'FME_NUM_CONDITIONS2___
    -> S50E150
S50E150: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-50,-30]
      NUM_TEST $(GEOM_maxLON) RANGE [150,180]
      NUM_TEST $(GEOM_maxLAT) RANGE [-50,-30]
      NUM_TEST $(GEOM_minLON) RANGE [150,180]
      NUM_TEST $(GEOM_minLAT) RANGE [-50,-30]
      NUM_TEST $(GEOM_minLON) RANGE [150,180]
      NUM_TEST $(GEOM_minLAT) RANGE [-50,-30]
      NUM_TEST $(GEOM_maxLON) RANGE [150,180]",<pass>
    <pass> -> FeatureReader_79 [INITIATOR]
FeatureReader_79
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_79
    ATTR_TABLE = SET_TO dataset_loc = FME_CONDITIONAL:DEFAULT_VALUE'fme://fme-server/50s030w_20101117_gmted_dsc075.tif?id=FME_SHAREDRESOURCE_DATA%2Ffilesys%2FHGDE%2FDEM%2FS50%2F50s030w_20101117_gmted_dsc075.tif&module=fmeserver&webservice=FME%20Server&connection=geopol'BOOL_OP;OR;COMPOSITE_TEST;1;TEST $(SERVER_MODE) = NO'$(FME_MF_DIR_ENCODED)DEM\S50\50s030w_20101117_gmted_dsc075.tif'FME_NUM_CONDITIONS2___
    -> S50W30
S50W30: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-50,-30]
      NUM_TEST $(GEOM_maxLON) RANGE [-30,0]
      NUM_TEST $(GEOM_maxLAT) RANGE [-50,-30]
      NUM_TEST $(GEOM_minLON) RANGE [-30,0]
      NUM_TEST $(GEOM_minLAT) RANGE [-50,-30]
      NUM_TEST $(GEOM_minLON) RANGE [-30,0]
      NUM_TEST $(GEOM_minLAT) RANGE [-50,-30]
      NUM_TEST $(GEOM_maxLON) RANGE [-30,0]",<pass>
    <pass> -> FeatureReader_75 [INITIATOR]
FeatureReader_75
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_80
    ATTR_TABLE = SET_TO dataset_loc = FME_CONDITIONAL:DEFAULT_VALUE'fme://fme-server/50s060w_20101117_gmted_dsc075.tif?id=FME_SHAREDRESOURCE_DATA%2Ffilesys%2FHGDE%2FDEM%2FS50%2F50s060w_20101117_gmted_dsc075.tif&module=fmeserver&webservice=FME%20Server&connection=geopol'BOOL_OP;OR;COMPOSITE_TEST;1;TEST $(SERVER_MODE) = NO'$(FME_MF_DIR_ENCODED)DEM\S50\50s060w_20101117_gmted_dsc075.tif'FME_NUM_CONDITIONS2___
    -> S50W60
S50W60: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-50,-30]
      NUM_TEST $(GEOM_maxLON) RANGE [-60,-30]
      NUM_TEST $(GEOM_maxLAT) RANGE [-50,-30]
      NUM_TEST $(GEOM_minLON) RANGE [-60,-30]
      NUM_TEST $(GEOM_minLAT) RANGE [-50,-30]
      NUM_TEST $(GEOM_minLON) RANGE [-60,-30]
      NUM_TEST $(GEOM_minLAT) RANGE [-50,-30]
      NUM_TEST $(GEOM_maxLON) RANGE [-60,-30]",<pass>
    <pass> -> FeatureReader_80 [INITIATOR]
FeatureReader_80
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_81
    ATTR_TABLE = SET_TO dataset_loc = FME_CONDITIONAL:DEFAULT_VALUE'fme://fme-server/50s090w_20101117_gmted_dsc075.tif?id=FME_SHAREDRESOURCE_DATA%2Ffilesys%2FHGDE%2FDEM%2FS50%2F50s090w_20101117_gmted_dsc075.tif&module=fmeserver&webservice=FME%20Server&connection=geopol'BOOL_OP;OR;COMPOSITE_TEST;1;TEST $(SERVER_MODE) = NO'$(FME_MF_DIR_ENCODED)DEM\S50\50s090w_20101117_gmted_dsc075.tif'FME_NUM_CONDITIONS2___
    -> S50W90
S50W90: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-50,-30]
      NUM_TEST $(GEOM_maxLON) RANGE [-90,-60]
      NUM_TEST $(GEOM_maxLAT) RANGE [-50,-30]
      NUM_TEST $(GEOM_minLON) RANGE [-90,-60]
      NUM_TEST $(GEOM_minLAT) RANGE [-50,-30]
      NUM_TEST $(GEOM_minLON) RANGE [-90,-60]
      NUM_TEST $(GEOM_minLAT) RANGE [-50,-30]
      NUM_TEST $(GEOM_maxLON) RANGE [-90,-60]",<pass>
    <pass> -> FeatureReader_81 [INITIATOR]
FeatureReader_81
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_82
    ATTR_TABLE = SET_TO dataset_loc = FME_CONDITIONAL:DEFAULT_VALUE'fme://fme-server/50s120w_20101117_gmted_dsc075.tif?id=FME_SHAREDRESOURCE_DATA%2Ffilesys%2FHGDE%2FDEM%2FS50%2F50s120w_20101117_gmted_dsc075.tif&module=fmeserver&webservice=FME%20Server&connection=geopol'BOOL_OP;OR;COMPOSITE_TEST;1;TEST $(SERVER_MODE) = NO'$(FME_MF_DIR_ENCODED)DEM\S50\50s120w_20101117_gmted_dsc075.tif'FME_NUM_CONDITIONS2___
    -> S50W120
S50W120: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-50,-30]
      NUM_TEST $(GEOM_maxLON) RANGE [-120,-90]
      NUM_TEST $(GEOM_maxLAT) RANGE [-50,-30]
      NUM_TEST $(GEOM_minLON) RANGE [-120,-90]
      NUM_TEST $(GEOM_minLAT) RANGE [-50,-30]
      NUM_TEST $(GEOM_minLON) RANGE [-120,-90]
      NUM_TEST $(GEOM_minLAT) RANGE [-50,-30]
      NUM_TEST $(GEOM_maxLON) RANGE [-120,-90]",<pass>
    <pass> -> FeatureReader_82 [INITIATOR]
FeatureReader_82
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_83
    ATTR_TABLE = SET_TO dataset_loc = FME_CONDITIONAL:DEFAULT_VALUE'fme://fme-server/50s150w_20101117_gmted_dsc075.tif?id=FME_SHAREDRESOURCE_DATA%2Ffilesys%2FHGDE%2FDEM%2FS50%2F50s150w_20101117_gmted_dsc075.tif&module=fmeserver&webservice=FME%20Server&connection=geopol'BOOL_OP;OR;COMPOSITE_TEST;1;TEST $(SERVER_MODE) = NO'$(FME_MF_DIR_ENCODED)DEM\S50\50s150w_20101117_gmted_dsc075.tif'FME_NUM_CONDITIONS2___
    -> S50W150
S50W150: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-50,-30]
      NUM_TEST $(GEOM_maxLON) RANGE [-150,-120]
      NUM_TEST $(GEOM_maxLAT) RANGE [-50,-30]
      NUM_TEST $(GEOM_minLON) RANGE [-150,-120]
      NUM_TEST $(GEOM_minLAT) RANGE [-50,-30]
      NUM_TEST $(GEOM_minLON) RANGE [-150,-120]
      NUM_TEST $(GEOM_minLAT) RANGE [-50,-30]
      NUM_TEST $(GEOM_maxLON) RANGE [-150,-120]",<pass>
    <pass> -> FeatureReader_83 [INITIATOR]
FeatureReader_83
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_84
    ATTR_TABLE = SET_TO dataset_loc = FME_CONDITIONAL:DEFAULT_VALUE'fme://fme-server/50s180w_20101117_gmted_dsc075.tif?id=FME_SHAREDRESOURCE_DATA%2Ffilesys%2FHGDE%2FDEM%2FS50%2F50s180w_20101117_gmted_dsc075.tif&module=fmeserver&webservice=FME%20Server&connection=geopol'BOOL_OP;OR;COMPOSITE_TEST;1;TEST $(SERVER_MODE) = NO'$(FME_MF_DIR_ENCODED)DEM\S50\50s180w_20101117_gmted_dsc075.tif'FME_NUM_CONDITIONS2___
    -> S50W180
S50W180: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-50,-30]
      NUM_TEST $(GEOM_maxLON) RANGE [-180,-150]
      NUM_TEST $(GEOM_maxLAT) RANGE [-50,-30]
      NUM_TEST $(GEOM_minLON) RANGE [-180,-150]
      NUM_TEST $(GEOM_minLAT) RANGE [-50,-30]
      NUM_TEST $(GEOM_minLON) RANGE [-180,-150]
      NUM_TEST $(GEOM_minLAT) RANGE [-50,-30]
      NUM_TEST $(GEOM_maxLON) RANGE [-180,-150]",<pass>
    <pass> -> FeatureReader_84 [INITIATOR]
FeatureReader_84
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_85
    ATTR_TABLE = SET_TO dataset_loc = FME_CONDITIONAL:DEFAULT_VALUE'fme://fme-server/70s000e_20101117_gmted_dsc075.tif?id=FME_SHAREDRESOURCE_DATA%2Ffilesys%2FHGDE%2FDEM%2FS70%2F70s000e_20101117_gmted_dsc075.tif&module=fmeserver&webservice=FME%20Server&connection=geopol'BOOL_OP;OR;COMPOSITE_TEST;1;TEST $(SERVER_MODE) = NO'$(FME_MF_DIR_ENCODED)DEM\S70\70s000e_20101117_gmted_dsc075.tif'FME_NUM_CONDITIONS2___
    -> S70E0
S70E0: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-70,-50]
      NUM_TEST $(GEOM_maxLON) RANGE [0,30]
      NUM_TEST $(GEOM_maxLAT) RANGE [-70,-50]
      NUM_TEST $(GEOM_minLON) RANGE [0,30]
      NUM_TEST $(GEOM_minLAT) RANGE [-70,-50]
      NUM_TEST $(GEOM_minLON) RANGE [0,30]
      NUM_TEST $(GEOM_minLAT) RANGE [-70,-50]
      NUM_TEST $(GEOM_maxLON) RANGE [0,30]",<pass>
    <pass> -> FeatureReader_86 [INITIATOR]
FeatureReader_86
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_86
    ATTR_TABLE = SET_TO dataset_loc = FME_CONDITIONAL:DEFAULT_VALUE'fme://fme-server/70s030e_20101117_gmted_dsc075.tif?id=FME_SHAREDRESOURCE_DATA%2Ffilesys%2FHGDE%2FDEM%2FS70%2F70s030e_20101117_gmted_dsc075.tif&module=fmeserver&webservice=FME%20Server&connection=geopol'BOOL_OP;OR;COMPOSITE_TEST;1;TEST $(SERVER_MODE) = NO'$(FME_MF_DIR_ENCODED)DEM\S70\70s030e_20101117_gmted_dsc075.tif'FME_NUM_CONDITIONS2___
    -> S70E30
S70E30: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-70,-50]
      NUM_TEST $(GEOM_maxLON) RANGE [30,60]
      NUM_TEST $(GEOM_maxLAT) RANGE [-70,-50]
      NUM_TEST $(GEOM_minLON) RANGE [30,60]
      NUM_TEST $(GEOM_minLAT) RANGE [-70,-50]
      NUM_TEST $(GEOM_minLON) RANGE [30,60]
      NUM_TEST $(GEOM_minLAT) RANGE [-70,-50]
      NUM_TEST $(GEOM_maxLON) RANGE [30,60]",<pass>
    <pass> -> FeatureReader_85 [INITIATOR]
FeatureReader_85
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_87
    ATTR_TABLE = SET_TO dataset_loc = FME_CONDITIONAL:DEFAULT_VALUE'fme://fme-server/70s060e_20101117_gmted_dsc075.tif?id=FME_SHAREDRESOURCE_DATA%2Ffilesys%2FHGDE%2FDEM%2FS70%2F70s060e_20101117_gmted_dsc075.tif&module=fmeserver&webservice=FME%20Server&connection=geopol'BOOL_OP;OR;COMPOSITE_TEST;1;TEST $(SERVER_MODE) = NO'$(FME_MF_DIR_ENCODED)DEM\S70\70s060e_20101117_gmted_dsc075.tif'FME_NUM_CONDITIONS2___
    -> S70E60
S70E60: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-70,-50]
      NUM_TEST $(GEOM_maxLON) RANGE [60,90]
      NUM_TEST $(GEOM_maxLAT) RANGE [-70,-50]
      NUM_TEST $(GEOM_minLON) RANGE [60,90]
      NUM_TEST $(GEOM_minLAT) RANGE [-70,-50]
      NUM_TEST $(GEOM_minLON) RANGE [60,90]
      NUM_TEST $(GEOM_minLAT) RANGE [-70,-50]
      NUM_TEST $(GEOM_maxLON) RANGE [60,90]",<pass>
    <pass> -> FeatureReader_88 [INITIATOR]
FeatureReader_88
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_88
    ATTR_TABLE = SET_TO dataset_loc = FME_CONDITIONAL:DEFAULT_VALUE'fme://fme-server/70s090e_20101117_gmted_dsc075.tif?id=FME_SHAREDRESOURCE_DATA%2Ffilesys%2FHGDE%2FDEM%2FS70%2F70s090e_20101117_gmted_dsc075.tif&module=fmeserver&webservice=FME%20Server&connection=geopol'BOOL_OP;OR;COMPOSITE_TEST;1;TEST $(SERVER_MODE) = NO'$(FME_MF_DIR_ENCODED)DEM\S70\70s090e_20101117_gmted_dsc075.tif'FME_NUM_CONDITIONS2___
    -> S70E90
S70E90: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-70,-50]
      NUM_TEST $(GEOM_maxLON) RANGE [90,120]
      NUM_TEST $(GEOM_maxLAT) RANGE [-70,-50]
      NUM_TEST $(GEOM_minLON) RANGE [90,120]
      NUM_TEST $(GEOM_minLAT) RANGE [-70,-50]
      NUM_TEST $(GEOM_minLON) RANGE [90,120]
      NUM_TEST $(GEOM_minLAT) RANGE [-70,-50]
      NUM_TEST $(GEOM_maxLON) RANGE [90,120]",<pass>
    <pass> -> FeatureReader_89 [INITIATOR]
FeatureReader_89
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_89
    ATTR_TABLE = SET_TO dataset_loc = FME_CONDITIONAL:DEFAULT_VALUE'fme://fme-server/70s120e_20101117_gmted_dsc075.tif?id=FME_SHAREDRESOURCE_DATA%2Ffilesys%2FHGDE%2FDEM%2FS70%2F70s120e_20101117_gmted_dsc075.tif&module=fmeserver&webservice=FME%20Server&connection=geopol'BOOL_OP;OR;COMPOSITE_TEST;1;TEST $(SERVER_MODE) = NO'$(FME_MF_DIR_ENCODED)DEM\S70\70s120e_20101117_gmted_dsc075.tif'FME_NUM_CONDITIONS2___
    -> S70E120
S70E120: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-70,-50]
      NUM_TEST $(GEOM_maxLON) RANGE [120,150]
      NUM_TEST $(GEOM_maxLAT) RANGE [-70,-50]
      NUM_TEST $(GEOM_minLON) RANGE [120,150]
      NUM_TEST $(GEOM_minLAT) RANGE [-70,-50]
      NUM_TEST $(GEOM_minLON) RANGE [120,150]
      NUM_TEST $(GEOM_minLAT) RANGE [-70,-50]
      NUM_TEST $(GEOM_maxLON) RANGE [120,150]",<pass>
    <pass> -> FeatureReader_90 [INITIATOR]
FeatureReader_90
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_90
    ATTR_TABLE = SET_TO dataset_loc = FME_CONDITIONAL:DEFAULT_VALUE'fme://fme-server/70s150e_20101117_gmted_dsc075.tif?id=FME_SHAREDRESOURCE_DATA%2Ffilesys%2FHGDE%2FDEM%2FS70%2F70s150e_20101117_gmted_dsc075.tif&module=fmeserver&webservice=FME%20Server&connection=geopol'BOOL_OP;OR;COMPOSITE_TEST;1;TEST $(SERVER_MODE) = NO'$(FME_MF_DIR_ENCODED)DEM\S70\70s150e_20101117_gmted_dsc075.tif'FME_NUM_CONDITIONS2___
    -> S70E150
S70E150: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-70,-50]
      NUM_TEST $(GEOM_maxLON) RANGE [150,180]
      NUM_TEST $(GEOM_maxLAT) RANGE [-70,-50]
      NUM_TEST $(GEOM_minLON) RANGE [150,180]
      NUM_TEST $(GEOM_minLAT) RANGE [-70,-50]
      NUM_TEST $(GEOM_minLON) RANGE [150,180]
      NUM_TEST $(GEOM_minLAT) RANGE [-70,-50]
      NUM_TEST $(GEOM_maxLON) RANGE [150,180]",<pass>
    <pass> -> FeatureReader_91 [INITIATOR]
FeatureReader_91
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_91
    ATTR_TABLE = SET_TO dataset_loc = FME_CONDITIONAL:DEFAULT_VALUE'fme://fme-server/70s030w_20101117_gmted_dsc075.tif?id=FME_SHAREDRESOURCE_DATA%2Ffilesys%2FHGDE%2FDEM%2FS70%2F70s030w_20101117_gmted_dsc075.tif&module=fmeserver&webservice=FME%20Server&connection=geopol'BOOL_OP;OR;COMPOSITE_TEST;1;TEST $(SERVER_MODE) = NO'$(FME_MF_DIR_ENCODED)DEM\S70\70s030w_20101117_gmted_dsc075.tif'FME_NUM_CONDITIONS2___
    -> S70W30
S70W30: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-70,-50]
      NUM_TEST $(GEOM_maxLON) RANGE [-30,0]
      NUM_TEST $(GEOM_maxLAT) RANGE [-70,-50]
      NUM_TEST $(GEOM_minLON) RANGE [-30,0]
      NUM_TEST $(GEOM_minLAT) RANGE [-70,-50]
      NUM_TEST $(GEOM_minLON) RANGE [-30,0]
      NUM_TEST $(GEOM_minLAT) RANGE [-70,-50]
      NUM_TEST $(GEOM_maxLON) RANGE [-30,0]",<pass>
    <pass> -> FeatureReader_87 [INITIATOR]
FeatureReader_87
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_92
    ATTR_TABLE = SET_TO dataset_loc = FME_CONDITIONAL:DEFAULT_VALUE'fme://fme-server/70s060w_20101117_gmted_dsc075.tif?id=FME_SHAREDRESOURCE_DATA%2Ffilesys%2FHGDE%2FDEM%2FS70%2F70s060w_20101117_gmted_dsc075.tif&module=fmeserver&webservice=FME%20Server&connection=geopol'BOOL_OP;OR;COMPOSITE_TEST;1;TEST $(SERVER_MODE) = NO'$(FME_MF_DIR_ENCODED)DEM\S70\70s060w_20101117_gmted_dsc075.tif'FME_NUM_CONDITIONS2___
    -> S70W60
S70W60: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-70,-50]
      NUM_TEST $(GEOM_maxLON) RANGE [-60,-30]
      NUM_TEST $(GEOM_maxLAT) RANGE [-70,-50]
      NUM_TEST $(GEOM_minLON) RANGE [-60,-30]
      NUM_TEST $(GEOM_minLAT) RANGE [-70,-50]
      NUM_TEST $(GEOM_minLON) RANGE [-60,-30]
      NUM_TEST $(GEOM_minLAT) RANGE [-70,-50]
      NUM_TEST $(GEOM_maxLON) RANGE [-60,-30]",<pass>
    <pass> -> FeatureReader_92 [INITIATOR]
FeatureReader_92
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_93
    ATTR_TABLE = SET_TO dataset_loc = FME_CONDITIONAL:DEFAULT_VALUE'fme://fme-server/70s090w_20101117_gmted_dsc075.tif?id=FME_SHAREDRESOURCE_DATA%2Ffilesys%2FHGDE%2FDEM%2FS70%2F70s090w_20101117_gmted_dsc075.tif&module=fmeserver&webservice=FME%20Server&connection=geopol'BOOL_OP;OR;COMPOSITE_TEST;1;TEST $(SERVER_MODE) = NO'$(FME_MF_DIR_ENCODED)DEM\S70\70s090w_20101117_gmted_dsc075.tif'FME_NUM_CONDITIONS2___
    -> S70W90
S70W90: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-70,-50]
      NUM_TEST $(GEOM_maxLON) RANGE [-90,-60]
      NUM_TEST $(GEOM_maxLAT) RANGE [-70,-50]
      NUM_TEST $(GEOM_minLON) RANGE [-90,-60]
      NUM_TEST $(GEOM_minLAT) RANGE [-70,-50]
      NUM_TEST $(GEOM_minLON) RANGE [-90,-60]
      NUM_TEST $(GEOM_minLAT) RANGE [-70,-50]
      NUM_TEST $(GEOM_maxLON) RANGE [-90,-60]",<pass>
    <pass> -> FeatureReader_93 [INITIATOR]
FeatureReader_93
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_94
    ATTR_TABLE = SET_TO dataset_loc = FME_CONDITIONAL:DEFAULT_VALUE'fme://fme-server/70s120w_20101117_gmted_dsc075.tif?id=FME_SHAREDRESOURCE_DATA%2Ffilesys%2FHGDE%2FDEM%2FS70%2F70s120w_20101117_gmted_dsc075.tif&module=fmeserver&webservice=FME%20Server&connection=geopol'BOOL_OP;OR;COMPOSITE_TEST;1;TEST $(SERVER_MODE) = NO'$(FME_MF_DIR_ENCODED)DEM\S70\70s120w_20101117_gmted_dsc075.tif'FME_NUM_CONDITIONS2___
    -> S70W120
S70W120: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-70,-50]
      NUM_TEST $(GEOM_maxLON) RANGE [-120,-90]
      NUM_TEST $(GEOM_maxLAT) RANGE [-70,-50]
      NUM_TEST $(GEOM_minLON) RANGE [-120,-90]
      NUM_TEST $(GEOM_minLAT) RANGE [-70,-50]
      NUM_TEST $(GEOM_minLON) RANGE [-120,-90]
      NUM_TEST $(GEOM_minLAT) RANGE [-70,-50]
      NUM_TEST $(GEOM_maxLON) RANGE [-120,-90]",<pass>
    <pass> -> FeatureReader_94 [INITIATOR]
FeatureReader_94
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_95
    ATTR_TABLE = SET_TO dataset_loc = FME_CONDITIONAL:DEFAULT_VALUE'fme://fme-server/70s150w_20101117_gmted_dsc075.tif?id=FME_SHAREDRESOURCE_DATA%2Ffilesys%2FHGDE%2FDEM%2FS70%2F70s150w_20101117_gmted_dsc075.tif&module=fmeserver&webservice=FME%20Server&connection=geopol'BOOL_OP;OR;COMPOSITE_TEST;1;TEST $(SERVER_MODE) = NO'$(FME_MF_DIR_ENCODED)DEM\S70\70s150w_20101117_gmted_dsc075.tif'FME_NUM_CONDITIONS2___
    -> S70W150
S70W150: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-70,-50]
      NUM_TEST $(GEOM_maxLON) RANGE [-150,-120]
      NUM_TEST $(GEOM_maxLAT) RANGE [-70,-50]
      NUM_TEST $(GEOM_minLON) RANGE [-150,-120]
      NUM_TEST $(GEOM_minLAT) RANGE [-70,-50]
      NUM_TEST $(GEOM_minLON) RANGE [-150,-120]
      NUM_TEST $(GEOM_minLAT) RANGE [-70,-50]
      NUM_TEST $(GEOM_maxLON) RANGE [-150,-120]",<pass>
    <pass> -> FeatureReader_95 [INITIATOR]
FeatureReader_95
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_96
    ATTR_TABLE = SET_TO dataset_loc = FME_CONDITIONAL:DEFAULT_VALUE'fme://fme-server/70s180w_20101117_gmted_dsc075.tif?id=FME_SHAREDRESOURCE_DATA%2Ffilesys%2FHGDE%2FDEM%2FS70%2F70s180w_20101117_gmted_dsc075.tif&module=fmeserver&webservice=FME%20Server&connection=geopol'BOOL_OP;OR;COMPOSITE_TEST;1;TEST $(SERVER_MODE) = NO'$(FME_MF_DIR_ENCODED)DEM\S70\70s180w_20101117_gmted_dsc075.tif'FME_NUM_CONDITIONS2___
    -> S70W180
S70W180: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-70,-50]
      NUM_TEST $(GEOM_maxLON) RANGE [-180,-150]
      NUM_TEST $(GEOM_maxLAT) RANGE [-70,-50]
      NUM_TEST $(GEOM_minLON) RANGE [-180,-150]
      NUM_TEST $(GEOM_minLAT) RANGE [-70,-50]
      NUM_TEST $(GEOM_minLON) RANGE [-180,-150]
      NUM_TEST $(GEOM_minLAT) RANGE [-70,-50]
      NUM_TEST $(GEOM_maxLON) RANGE [-180,-150]",<pass>
    <pass> -> FeatureReader_96 [INITIATOR]
FeatureReader_96
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_97
    ATTR_TABLE = SET_TO dataset_loc = FME_CONDITIONAL:DEFAULT_VALUE'fme://fme-server/90s000e_20101117_gmted_dsc075.tif?id=FME_SHAREDRESOURCE_DATA%2Ffilesys%2FHGDE%2FDEM%2FS90%2F90s000e_20101117_gmted_dsc075.tif&module=fmeserver&webservice=FME%20Server&connection=geopol'BOOL_OP;OR;COMPOSITE_TEST;1;TEST $(SERVER_MODE) = NO'$(FME_MF_DIR_ENCODED)DEM\S90\90s000e_20101117_gmted_dsc300.tif'FME_NUM_CONDITIONS2___
    -> S90E0
S90E0: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-90,-70]
      NUM_TEST $(GEOM_maxLON) RANGE [0,30]
      NUM_TEST $(GEOM_maxLAT) RANGE [-90,-70]
      NUM_TEST $(GEOM_minLON) RANGE [0,30]
      NUM_TEST $(GEOM_minLAT) RANGE [-90,-70]
      NUM_TEST $(GEOM_minLON) RANGE [0,30]
      NUM_TEST $(GEOM_minLAT) RANGE [-90,-70]
      NUM_TEST $(GEOM_maxLON) RANGE [0,30]",<pass>
    <pass> -> FeatureReader_98 [INITIATOR]
FeatureReader_98
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_98
    ATTR_TABLE = SET_TO dataset_loc = FME_CONDITIONAL:DEFAULT_VALUE'fme://fme-server/90s030e_20101117_gmted_dsc075.tif?id=FME_SHAREDRESOURCE_DATA%2Ffilesys%2FHGDE%2FDEM%2FS90%2F90s030e_20101117_gmted_dsc075.tif&module=fmeserver&webservice=FME%20Server&connection=geopol'BOOL_OP;OR;COMPOSITE_TEST;1;TEST $(SERVER_MODE) = NO'$(FME_MF_DIR_ENCODED)DEM\S90\90s030e_20101117_gmted_dsc300.tif'FME_NUM_CONDITIONS2___
    -> S90E30
S90E30: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-90,-70]
      NUM_TEST $(GEOM_maxLON) RANGE [30,60]
      NUM_TEST $(GEOM_maxLAT) RANGE [-90,-70]
      NUM_TEST $(GEOM_minLON) RANGE [30,60]
      NUM_TEST $(GEOM_minLAT) RANGE [-90,-70]
      NUM_TEST $(GEOM_minLON) RANGE [30,60]
      NUM_TEST $(GEOM_minLAT) RANGE [-90,-70]
      NUM_TEST $(GEOM_maxLON) RANGE [30,60]",<pass>
    <pass> -> FeatureReader_97 [INITIATOR]
FeatureReader_97
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_99
    ATTR_TABLE = SET_TO dataset_loc = FME_CONDITIONAL:DEFAULT_VALUE'fme://fme-server/90s060e_20101117_gmted_dsc075.tif?id=FME_SHAREDRESOURCE_DATA%2Ffilesys%2FHGDE%2FDEM%2FS90%2F90s060e_20101117_gmted_dsc075.tif&module=fmeserver&webservice=FME%20Server&connection=geopol'BOOL_OP;OR;COMPOSITE_TEST;1;TEST $(SERVER_MODE) = NO'$(FME_MF_DIR_ENCODED)DEM\S90\90s060e_20101117_gmted_dsc300.tif'FME_NUM_CONDITIONS2___
    -> S90E60
S90E60: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-90,-70]
      NUM_TEST $(GEOM_maxLON) RANGE [60,90]
      NUM_TEST $(GEOM_maxLAT) RANGE [-90,-70]
      NUM_TEST $(GEOM_minLON) RANGE [60,90]
      NUM_TEST $(GEOM_minLAT) RANGE [-90,-70]
      NUM_TEST $(GEOM_minLON) RANGE [60,90]
      NUM_TEST $(GEOM_minLAT) RANGE [-90,-70]
      NUM_TEST $(GEOM_maxLON) RANGE [60,90]",<pass>
    <pass> -> FeatureReader_100 [INITIATOR]
FeatureReader_100
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_100
    ATTR_TABLE = SET_TO dataset_loc = FME_CONDITIONAL:DEFAULT_VALUE'fme://fme-server/90s090e_20101117_gmted_dsc075.tif?id=FME_SHAREDRESOURCE_DATA%2Ffilesys%2FHGDE%2FDEM%2FS90%2F90s090e_20101117_gmted_dsc075.tif&module=fmeserver&webservice=FME%20Server&connection=geopol'BOOL_OP;OR;COMPOSITE_TEST;1;TEST $(SERVER_MODE) = NO'$(FME_MF_DIR_ENCODED)DEM\S90\90s090e_20101117_gmted_dsc300.tif'FME_NUM_CONDITIONS2___
    -> S90E90
S90E90: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-90,-70]
      NUM_TEST $(GEOM_maxLON) RANGE [90,120]
      NUM_TEST $(GEOM_maxLAT) RANGE [-90,-70]
      NUM_TEST $(GEOM_minLON) RANGE [90,120]
      NUM_TEST $(GEOM_minLAT) RANGE [-90,-70]
      NUM_TEST $(GEOM_minLON) RANGE [90,120]
      NUM_TEST $(GEOM_minLAT) RANGE [-90,-70]
      NUM_TEST $(GEOM_maxLON) RANGE [90,120]",<pass>
    <pass> -> FeatureReader_101 [INITIATOR]
FeatureReader_101
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_101
    ATTR_TABLE = SET_TO dataset_loc = FME_CONDITIONAL:DEFAULT_VALUE'fme://fme-server/90s120e_20101117_gmted_dsc075.tif?id=FME_SHAREDRESOURCE_DATA%2Ffilesys%2FHGDE%2FDEM%2FS90%2F90s0120e_20101117_gmted_dsc075.tif&module=fmeserver&webservice=FME%20Server&connection=geopol'BOOL_OP;OR;COMPOSITE_TEST;1;TEST $(SERVER_MODE) = NO'$(FME_MF_DIR_ENCODED)DEM\S90\90s120e_20101117_gmted_dsc300.tif'FME_NUM_CONDITIONS2___
    -> S90E120
S90E120: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-90,-70]
      NUM_TEST $(GEOM_maxLON) RANGE [120,150]
      NUM_TEST $(GEOM_maxLAT) RANGE [-90,-70]
      NUM_TEST $(GEOM_minLON) RANGE [120,150]
      NUM_TEST $(GEOM_minLAT) RANGE [-90,-70]
      NUM_TEST $(GEOM_minLON) RANGE [120,150]
      NUM_TEST $(GEOM_minLAT) RANGE [-90,-70]
      NUM_TEST $(GEOM_maxLON) RANGE [120,150]",<pass>
    <pass> -> FeatureReader_102 [INITIATOR]
FeatureReader_102
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_102
    ATTR_TABLE = SET_TO dataset_loc = FME_CONDITIONAL:DEFAULT_VALUE'fme://fme-server/90s150e_20101117_gmted_dsc075.tif?id=FME_SHAREDRESOURCE_DATA%2Ffilesys%2FHGDE%2FDEM%2FS90%2F90s150e_20101117_gmted_dsc075.tif&module=fmeserver&webservice=FME%20Server&connection=geopol'BOOL_OP;OR;COMPOSITE_TEST;1;TEST $(SERVER_MODE) = NO'$(FME_MF_DIR_ENCODED)DEM\S90\90s150e_20101117_gmted_dsc300.tif'FME_NUM_CONDITIONS2___
    -> S90E150
S90E150: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-90,-70]
      NUM_TEST $(GEOM_maxLON) RANGE [150,180]
      NUM_TEST $(GEOM_maxLAT) RANGE [-90,-70]
      NUM_TEST $(GEOM_minLON) RANGE [150,180]
      NUM_TEST $(GEOM_minLAT) RANGE [-90,-70]
      NUM_TEST $(GEOM_minLON) RANGE [150,180]
      NUM_TEST $(GEOM_minLAT) RANGE [-90,-70]
      NUM_TEST $(GEOM_maxLON) RANGE [150,180]",<pass>
    <pass> -> FeatureReader_103 [INITIATOR]
FeatureReader_103
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_103
    ATTR_TABLE = SET_TO dataset_loc = FME_CONDITIONAL:DEFAULT_VALUE'fme://fme-server/90s030w_20101117_gmted_dsc075.tif?id=FME_SHAREDRESOURCE_DATA%2Ffilesys%2FHGDE%2FDEM%2FS90%2F90s030w_20101117_gmted_dsc075.tif&module=fmeserver&webservice=FME%20Server&connection=geopol'BOOL_OP;OR;COMPOSITE_TEST;1;TEST $(SERVER_MODE) = NO'$(FME_MF_DIR_ENCODED)DEM\S90\90s030w_20101117_gmted_dsc300.tif'FME_NUM_CONDITIONS2___
    -> S90W30
S90W30: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-90,-70]
      NUM_TEST $(GEOM_maxLON) RANGE [-30,0]
      NUM_TEST $(GEOM_maxLAT) RANGE [-90,-70]
      NUM_TEST $(GEOM_minLON) RANGE [-30,0]
      NUM_TEST $(GEOM_minLAT) RANGE [-90,-70]
      NUM_TEST $(GEOM_minLON) RANGE [-30,0]
      NUM_TEST $(GEOM_minLAT) RANGE [-90,-70]
      NUM_TEST $(GEOM_maxLON) RANGE [-30,0]",<pass>
    <pass> -> FeatureReader_99 [INITIATOR]
FeatureReader_99
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_104
    ATTR_TABLE = SET_TO dataset_loc = FME_CONDITIONAL:DEFAULT_VALUE'fme://fme-server/90s060w_20101117_gmted_dsc075.tif?id=FME_SHAREDRESOURCE_DATA%2Ffilesys%2FHGDE%2FDEM%2FS90%2F90s060w_20101117_gmted_dsc075.tif&module=fmeserver&webservice=FME%20Server&connection=geopol'BOOL_OP;OR;COMPOSITE_TEST;1;TEST $(SERVER_MODE) = NO'$(FME_MF_DIR_ENCODED)DEM\S90\90s060w_20101117_gmted_dsc300.tif'FME_NUM_CONDITIONS2___
    -> S90W60
S90W60: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-90,-70]
      NUM_TEST $(GEOM_maxLON) RANGE [-60,-30]
      NUM_TEST $(GEOM_maxLAT) RANGE [-90,-70]
      NUM_TEST $(GEOM_minLON) RANGE [-60,-30]
      NUM_TEST $(GEOM_minLAT) RANGE [-90,-70]
      NUM_TEST $(GEOM_minLON) RANGE [-60,-30]
      NUM_TEST $(GEOM_minLAT) RANGE [-90,-70]
      NUM_TEST $(GEOM_maxLON) RANGE [-60,-30]",<pass>
    <pass> -> FeatureReader_104 [INITIATOR]
FeatureReader_104
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_105
    ATTR_TABLE = SET_TO dataset_loc = FME_CONDITIONAL:DEFAULT_VALUE'fme://fme-server/90s090w_20101117_gmted_dsc075.tif?id=FME_SHAREDRESOURCE_DATA%2Ffilesys%2FHGDE%2FDEM%2FS90%2F90s090w_20101117_gmted_dsc075.tif&module=fmeserver&webservice=FME%20Server&connection=geopol'BOOL_OP;OR;COMPOSITE_TEST;1;TEST $(SERVER_MODE) = NO'$(FME_MF_DIR_ENCODED)DEM\S90\90s090w_20101117_gmted_dsc300.tif'FME_NUM_CONDITIONS2___
    -> 90W90
90W90: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-90,-70]
      NUM_TEST $(GEOM_maxLON) RANGE [-90,-60]
      NUM_TEST $(GEOM_maxLAT) RANGE [-90,-70]
      NUM_TEST $(GEOM_minLON) RANGE [-90,-60]
      NUM_TEST $(GEOM_minLAT) RANGE [-90,-70]
      NUM_TEST $(GEOM_minLON) RANGE [-90,-60]
      NUM_TEST $(GEOM_minLAT) RANGE [-90,-70]
      NUM_TEST $(GEOM_maxLON) RANGE [-90,-60]",<pass>
    <pass> -> FeatureReader_105 [INITIATOR]
FeatureReader_105
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_106
    ATTR_TABLE = SET_TO dataset_loc = FME_CONDITIONAL:DEFAULT_VALUE'fme://fme-server/90s120w_20101117_gmted_dsc075.tif?id=FME_SHAREDRESOURCE_DATA%2Ffilesys%2FHGDE%2FDEM%2FS90%2F90s120w_20101117_gmted_dsc075.tif&module=fmeserver&webservice=FME%20Server&connection=geopol'BOOL_OP;OR;COMPOSITE_TEST;1;TEST $(SERVER_MODE) = NO'$(FME_MF_DIR_ENCODED)DEM\S90\90s120w_20101117_gmted_dsc300.tif'FME_NUM_CONDITIONS2___
    -> S90W120
S90W120: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-90,-70]
      NUM_TEST $(GEOM_maxLON) RANGE [-120,-90]
      NUM_TEST $(GEOM_maxLAT) RANGE [-90,-70]
      NUM_TEST $(GEOM_minLON) RANGE [-120,-90]
      NUM_TEST $(GEOM_minLAT) RANGE [-90,-70]
      NUM_TEST $(GEOM_minLON) RANGE [-120,-90]
      NUM_TEST $(GEOM_minLAT) RANGE [-90,-70]
      NUM_TEST $(GEOM_maxLON) RANGE [-120,-90]",<pass>
    <pass> -> FeatureReader_106 [INITIATOR]
FeatureReader_106
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_107
    ATTR_TABLE = SET_TO dataset_loc = FME_CONDITIONAL:DEFAULT_VALUE'fme://fme-server/90s150w_20101117_gmted_dsc075.tif?id=FME_SHAREDRESOURCE_DATA%2Ffilesys%2FHGDE%2FDEM%2FS90%2F90s150w_20101117_gmted_dsc075.tif&module=fmeserver&webservice=FME%20Server&connection=geopol'BOOL_OP;OR;COMPOSITE_TEST;1;TEST $(SERVER_MODE) = NO'$(FME_MF_DIR_ENCODED)DEM\S90\90s150w_20101117_gmted_dsc300.tif'FME_NUM_CONDITIONS2___
    -> S90W150
S90W150: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-90,-70]
      NUM_TEST $(GEOM_maxLON) RANGE [-150,-120]
      NUM_TEST $(GEOM_maxLAT) RANGE [-90,-70]
      NUM_TEST $(GEOM_minLON) RANGE [-150,-120]
      NUM_TEST $(GEOM_minLAT) RANGE [-90,-70]
      NUM_TEST $(GEOM_minLON) RANGE [-150,-120]
      NUM_TEST $(GEOM_minLAT) RANGE [-90,-70]
      NUM_TEST $(GEOM_maxLON) RANGE [-150,-120]",<pass>
    <pass> -> FeatureReader_107 [INITIATOR]
FeatureReader_107
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
AttributeManager_108
    ATTR_TABLE = SET_TO dataset_loc = FME_CONDITIONAL:DEFAULT_VALUE'fme://fme-server/90s180w_20101117_gmted_dsc075.tif?id=FME_SHAREDRESOURCE_DATA%2Ffilesys%2FHGDE%2FDEM%2FS90%2F90s180w_20101117_gmted_dsc075.tif&module=fmeserver&webservice=FME%20Server&connection=geopol'BOOL_OP;OR;COMPOSITE_TEST;1;TEST $(SERVER_MODE) = NO'$(FME_MF_DIR_ENCODED)DEM\S90\90s180w_20101117_gmted_dsc300.tif'FME_NUM_CONDITIONS2___
    -> S90W180
S90W180: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-90,-70]
      NUM_TEST $(GEOM_maxLON) RANGE [-180,-150]
      NUM_TEST $(GEOM_maxLAT) RANGE [-90,-70]
      NUM_TEST $(GEOM_minLON) RANGE [-180,-150]
      NUM_TEST $(GEOM_minLAT) RANGE [-90,-70]
      NUM_TEST $(GEOM_minLON) RANGE [-180,-150]
      NUM_TEST $(GEOM_minLAT) RANGE [-90,-70]
      NUM_TEST $(GEOM_maxLON) RANGE [-180,-150]",<pass>
    <pass> -> FeatureReader_108 [INITIATOR]
FeatureReader_108
    ATTR_ACCUM_MODE = Only Use Result
    COMBINE_GEOM = Use Result
    COORDSYS = LL-WGS84
    DATASET = @Value(dataset_loc)
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    <OTHER> -> RasterMosaicker_2
RasterMosaicker_2
    ACCUM_ATTRS_NAME = Use Attributes From One Feature
    INTERPOLATION_TYPE_NAME = Nearest Neighbor
    MERGE_PALETTES_NAME = Yes
    NODATA_OVERWRITE = No
    OVERLAPPING_VALUES = last
    SNAPPING_TYPE_NAME = Offset
    -> Clipper [CLIPPEE]
Creator
    COORDS = $(GEOM_minLON) $(GEOM_minLAT) $(GEOM_maxLON) $(GEOM_maxLAT)
    COORDSYS = LL-WGS84
    GEOMTYPE = 2D Min/Max Box
    NUM = 1
    CREATED -> Clipper [CLIPPER]
Clipper
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    INSIDE -> DEM_full (writer GEOTIFF_1)

Bookmark: Writer Feature Types
DEM_full (writer GEOTIFF_1)
