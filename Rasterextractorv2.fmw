FME workspace Rasterextractorv2.fmw
Title: Geospatial PDF - Cartographic Output

Parameters:
- zoom = 13
- x_1 = 4252   # x tile number
- x_2 = 4252   # x tile number
- x_3 = 4253   # x tile number
- x_4 = 4253   # x tile number
- x_5 = 4252   # x tile number
- x_6 = 4252   # x tile number
- x_7 = 4252   # x tile number
- x_8 = 4252   # x tile number
- x_9 = 4252   # x tile number
- y_1 = 2896   # y tile number
- y_2 = 2897   # y tile number
- y_3 = 2896   # y tile number
- y_4 = 2897   # y tile number
- y_5 = 2896   # y tile number
- y_6 = 2896   # y tile number
- y_7 = 2896   # y tile number
- y_8 = 2896   # y tile number
- y_9 = 2896   # y tile number
- x_deg_1 = 6.85546875   # longitude 
- x_deg_2 = 6.85546875   # longitude 
- x_deg_3 = 6.8994140625   # longitude 
- x_deg_4 = 6.8994140625   # longitude 
- x_deg_5 = 6.85546875   # longitude 
- x_deg_6 = 6.85546875   # longitude 
- x_deg_7 = 6.85546875   # longitude 
- x_deg_8 = 6.85546875   # longitude 
- x_deg_9 = 6.85546875   # longitude 
- y_deg_1 = 46.55886030311718   # latitude 
- y_deg_2 = 46.52863469527168   # latitude 
- y_deg_3 = 46.55886030311718   # latitude 
- y_deg_4 = 46.52863469527168   # latitude 
- y_deg_5 = 46.55886030311718   # latitude 
- y_deg_6 = 46.55886030311718   # latitude 
- y_deg_7 = 46.55886030311718   # latitude 
- y_deg_8 = 46.55886030311718   # latitude 
- y_deg_9 = 46.55886030311718   # latitude 
- min_lon = 6.87041349   # bb min lon
- min_lat = 46.5104134960690   # bb min lat
- max_lon = 6.9095865039309   # bb max lon
- max_lat = 46.5495865   # bb max lat
- DestDataset_JPEG = $(FME_MF_DIR)outputPDF   # Destination JPEG Folder
- DestDataset_PNGRASTER = $(FME_MF_DIR)outputPDF   # Destination PNG (Portable Network Graphics) Folder
- DestDataset_JPEG2000 = $(FME_MF_DIR)outputPDF   # Destination JPEG 2000 Folder
- BASEMAPE = http://tile.stamen.com/terrain-background   # URL of the basemap
- BASEMAPE_ext = .png   # extention of the basemap
- ISO_code = test_10   # Iso code of the extract

Writers:
- JPEG_1: JPEG to $(DestDataset_JPEG)
- JPEG2000_1: JPEG2000 to $(DestDataset_JPEG2000)
- PNGRASTER_1: PNGRASTER to $(DestDataset_PNGRASTER)
- JPEG_2: JPEG to $(DestDataset_JPEG)

Creator_1
    GEOMTYPE = Geometry Object
    NUM = 1
    CREATED -> Cloner
Cloner
    COPIES = 9
    COPYATT = _copynum
    COPY -> AttributeCreator
AttributeCreator
    ATTR_TABLE:
      SET_TO xtile = FME_CONDITIONAL:DEFAULT_VALUE'_FME_NO_OP_'BOOL_OP;OR;COMPOSITE_TEST;1;TEST @Value(_copynum) = 0'$(x_1)'BOOL_OP;OR;COMPOSITE_TEST;1;TEST @Value(_copynum) = 1'$(x_2)'BOOL_OP;OR;COMPOSITE_TEST;1;TEST @Value(_copynum) = 2'$(x_3)'BOOL_OP;OR;COMPOSITE_TEST;1;TEST @Value(_copynum) = 3'$(x_4)'BOOL_OP;OR;COMPOSITE_TEST;1;TEST @Value(_copynum) = 4'$(x_5)'BOOL_OP;OR;COMPOSITE_TEST;1;TEST @Value(_copynum) = 5'$(x_6)'BOOL_OP;OR;COMPOSITE_TEST;1;TEST @Value(_copynum) = 6'$(x_7)'BOOL_OP;OR;COMPOSITE_TEST;1;TEST @Value(_copynum) = 7'$(x_8)'BOOL_OP;OR;COMPOSITE_TEST;1;TEST @Value(_copynum) = 8'$(x_9)'FME_NUM_CONDITIONS10___
      SET_TO ytile = FME_CONDITIONAL:DEFAULT_VALUE'_FME_NO_OP_'BOOL_OP;OR;COMPOSITE_TEST;1;TEST @Value(_copynum) = 0'$(y_1)'BOOL_OP;OR;COMPOSITE_TEST;1;TEST @Value(_copynum) = 1'$(y_2)'BOOL_OP;OR;COMPOSITE_TEST;1;TEST @Value(_copynum) = 2'$(y_3)'BOOL_OP;OR;COMPOSITE_TEST;1;TEST @Value(_copynum) = 3'$(y_4)'BOOL_OP;OR;COMPOSITE_TEST;1;TEST @Value(_copynum) = 4'$(y_5)'BOOL_OP;OR;COMPOSITE_TEST;1;TEST @Value(_copynum) = 5'$(y_6)'BOOL_OP;OR;COMPOSITE_TEST;1;TEST @Value(_copynum) = 6'$(y_7)'BOOL_OP;OR;COMPOSITE_TEST;1;TEST @Value(_copynum) = 7'$(y_8)'BOOL_OP;OR;COMPOSITE_TEST;1;TEST @Value(_copynum) = 8'$(y_9)'FME_NUM_CONDITIONS10___
      SET_TO xcorner = FME_CONDITIONAL:DEFAULT_VALUE'_FME_NO_OP_'BOOL_OP;OR;COMPOSITE_TEST;1;TEST @Value(_copynum) = 0'$(x_deg_1)'BOOL_OP;OR;COMPOSITE_TEST;1;TEST @Value(_copynum) = 1'$(x_deg_2)'BOOL_OP;OR;COMPOSITE_TEST;1;TEST @Value(_copynum) = 2'$(x_deg_3)'BOOL_OP;OR;COMPOSITE_TEST;1;TEST @Value(_copynum) = 3'$(x_deg_4)'BOOL_OP;OR;COMPOSITE_TEST;1;TEST @Value(_copynum) = 4'$(x_deg_5)'BOOL_OP;OR;COMPOSITE_TEST;1;TEST @Value(_copynum) = 5'$(x_deg_6)'BOOL_OP;OR;COMPOSITE_TEST;1;TEST @Value(_copynum) = 6'$(x_deg_7)'BOOL_OP;OR;COMPOSITE_TEST;1;TEST @Value(_copynum) = 7'$(x_deg_8)'BOOL_OP;OR;COMPOSITE_TEST;1;TEST @Value(_copynum) = 8'$(x_deg_9)'FME_NUM_CONDITIONS10___
      SET_TO ycorner = FME_CONDITIONAL:DEFAULT_VALUE'_FME_NO_OP_'BOOL_OP;OR;COMPOSITE_TEST;1;TEST @Value(_copynum) = 0'$(y_deg_1)'BOOL_OP;OR;COMPOSITE_TEST;1;TEST @Value(_copynum) = 1'$(y_deg_2)'BOOL_OP;OR;COMPOSITE_TEST;1;TEST @Value(_copynum) = 2'$(y_deg_3)'BOOL_OP;OR;COMPOSITE_TEST;1;TEST @Value(_copynum) = 3'$(y_deg_4)'BOOL_OP;OR;COMPOSITE_TEST;1;TEST @Value(_copynum) = 4'$(y_deg_5)'BOOL_OP;OR;COMPOSITE_TEST;1;TEST @Value(_copynum) = 5'$(y_deg_6)'BOOL_OP;OR;COMPOSITE_TEST;1;TEST @Value(_copynum) = 6'$(y_deg_7)'BOOL_OP;OR;COMPOSITE_TEST;1;TEST @Value(_copynum) = 7'$(y_deg_8)'BOOL_OP;OR;COMPOSITE_TEST;1;TEST @Value(_copynum) = 8'$(y_deg_9)'FME_NUM_CONDITIONS10___
    -> AttributeManager
AttributeManager
    ATTR_TABLE:
      SET_TO UL_x = @Value(xcorner)
      SET_TO UL_y = @Value(ycorner)
      SET_TO UR_x = @Value(xcorner)+(360/@pow(2,$(zoom)))
      SET_TO UR_y = @Value(ycorner)
      SET_TO LL_x = @Value(xcorner)
      SET_TO LL_y = @Value(ycorner) - (360/@pow(2,$(zoom)))*@cos((@Value(ycorner)-360/(@pow(2,$(zoom)+1)))*@pi()/180)
      SET_TO LR_x = @Value(xcorner)+(360/@pow(2,$(zoom)))
      SET_TO LR_y = @Value(ycorner) - (360/@pow(2,$(zoom)))*@cos((@Value(ycorner)-360/(@pow(2,$(zoom)+1)))*@pi()/180)
    -> TestFilter
TestFilter
    DEFAULT_VALUE = delete
    TEST_LIST:
      "BOOL_OP,COMPOSITE,COMPOSITE_TEST,""""""( 1 OR 2 ) OR ( 3 )"""""",TEST_CLAUSE,TEST @Value(xtile) != $(x_1)
      TEST @Value(ytile) != $(y_1)
      TEST @Value(_copynum) = 0",pass
    pass -> TestFilter_17
TestFilter_17
    DEFAULT_VALUE = jpg
    TEST_LIST = "BOOL_OP,OR,COMPOSITE_TEST,""""""1"""""",TEST_CLAUSE,TEST $(BASEMAPE_ext) = .png",png
    png -> AttributeManager_2
    jpg -> TestFilter_2
AttributeManager_2
    ATTR_TABLE = SET_TO URL_BM = $(BASEMAPE)/$(zoom)/@Value(xtile)/@Value(ytile).png
    -> FeatureReader_12 [INITIATOR]
FeatureReader_12
    ATTR_ACCUM_MODE = Merge Initiator and Result
    ATTR_CONFLICT_RES = Use Result
    ATTR_IGNORE_NULLS = No
    COMBINE_GEOM = Use Result
    COORDSYS = LL-WGS84
    DATASET = @Value(URL_BM)
    FORMAT = PNGRASTER
    INTERACT = <No Spatial Filter>
    OUTPUT_FEATURES_DISPLAY = Schema and Data Features
    PNGRASTER_GROUP_BY_DATASET = No
    PNGRASTER_READER_META_ATTRIBUTES = fme_dataset fme_basename
    PNGRASTER_USE_SEARCH_ENVELOPE = NO
    <OTHER> -> RasterPaletteResolver_10
TestFilter_2
    DEFAULT_VALUE = BLUEMARBLE
    TEST_LIST = "BOOL_OP,OR,COMPOSITE_TEST,""""""1"""""",TEST_CLAUSE,CASE_INSENSITIVE_TEST $(BASEMAPE) CONTAINS arcgisonline.com",ARCGIS
    ARCGIS -> AttributeManager_3
    BLUEMARBLE -> AttributeManager_4
AttributeManager_3
    ATTR_TABLE = SET_TO URL_BM = $(BASEMAPE)/$(zoom)/@Value(ytile)/@Value(xtile).jpg
    -> FeatureReader_11 [INITIATOR]
AttributeManager_4
    ATTR_TABLE = SET_TO URL_BM = $(BASEMAPE)/$(zoom)-r@Value(ytile)-c@Value(xtile).jpg
    -> FeatureReader_11 [INITIATOR]
FeatureReader_11
    ATTR_ACCUM_MODE = Merge Initiator and Result
    ATTR_CONFLICT_RES = Use Result
    ATTR_IGNORE_NULLS = No
    COMBINE_GEOM = Use Result
    COORDSYS = LL-WGS84
    DATASET = @Value(URL_BM)
    FORMAT = JPEG
    INTERACT = <No Spatial Filter>
    JPEG_ALL_ATTRS_STARTING_WITH_EXIF_ARE_FORMAT_ATTRS = YES
    JPEG_APPLY_EXIF_ORIENTATION = Yes
    JPEG_APPLY_GCPS = NO
    JPEG_GROUP_BY_DATASET = No
    JPEG_READER_META_ATTRIBUTES = fme_dataset fme_basename
    JPEG_USE_SEARCH_ENVELOPE = NO
    OUTPUT_FEATURES_DISPLAY = Schema and Data Features
    <OTHER> -> RasterPaletteResolver_10
RasterPaletteResolver_10
    -> RasterGeoreferencer_10
RasterGeoreferencer_10
    POINTANDANGLE_OR_EXTENTS = Extents
    X_LL_COORD = @Value(LL_x)
    X_LR_COORD = @Value(LR_x)
    X_UL_COORD = @Value(UL_x)
    X_UR_COORD = @Value(UR_x)
    Y_LL_COORD = @Value(LL_y)
    Y_LR_COORD = @Value(LR_y)
    Y_UL_COORD = @Value(UL_y)
    Y_UR_COORD = @Value(UR_y)
    -> RasterMosaicker
RasterMosaicker
    ACCUM_ATTRS_NAME = Use Attributes From One Feature
    INTERPOLATION_TYPE_NAME = Nearest Neighbor
    MERGE_PALETTES_NAME = Yes
    NODATA_OVERWRITE = No
    OVERLAPPING_VALUES = last
    SNAPPING_TYPE_NAME = Offset
    -> Clipper_2 [CLIPPEE]
Creator_4
    COORDS = $(max_lon) $(max_lat) $(max_lon) $(min_lat) $(min_lon) $(min_lat) $(min_lon) $(max_lat) $(max_lon) $(max_lat)
    COORDSYS = LL-WGS84
    GEOMTYPE = 2D Coordinate List
    NUM = 1
    CREATED -> Clipper_2 [CLIPPER]
Clipper_2
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    INSIDE -> JPEG200000 (writer JPEG2000_1)
    INSIDE -> Raster1 (writer PNGRASTER_1)
    INSIDE -> Raster1 (writer JPEG_2)
Raster1 (writer JPEG_2)
    attributes: xtile char(200), ytile char(200), xcorner char(200), ycorner char(200), _creation_instance decimal(20,0), _copynum char(200), UL_x char(200), UL_y char(200), UR_x char(200), UR_y char(200), LL_x char(200), LL_y char(200), LR_x char(200), LR_y char(200), URL_BM char(200), _clipped char(200)
Raster1 (writer PNGRASTER_1)
    attributes: xtile char(200), ytile char(200), xcorner char(200), ycorner char(200), _creation_instance decimal(20,0), _copynum char(200), UL_x char(200), UL_y char(200), UR_x char(200), UR_y char(200), LL_x char(200), LL_y char(200), LR_x char(200), LR_y char(200), URL_BM char(200), _clipped char(200)
JPEG200000 (writer JPEG2000_1)
