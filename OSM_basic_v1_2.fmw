FME workspace OSM_basic_v1_2.fmw

Parameters:
- FEATURETYPES = building highway boundary place   # Feature Types to Read
- URL_DL_1 = https://download.geofabrik.de/europe/france/champagne-ardenne-latest.osm.pbf   # URL for OSM DL
- URL_DL_2 = https://download.geofabrik.de/europe/belgium-latest.osm.pbf   # URL for OSM DL
- URL_DL_3 = https://download.geofabrik.de/europe/france/champagne-ardenne-latest.osm.pbf   # URL for OSM DL
- URL_DL_4 = https://download.geofabrik.de/europe/france/champagne-ardenne-latest.osm.pbf   # URL for OSM DL
- URL_DL_5 = https://download.geofabrik.de/europe/france/champagne-ardenne-latest.osm.pbf   # URL for OSM DL
- URL_DL_6 = https://download.geofabrik.de/europe/france/champagne-ardenne-latest.osm.pbf   # URL for OSM DL
- URL_DL_7 = https://download.geofabrik.de/europe/france/champagne-ardenne-latest.osm.pbf   # URL for OSM DL
- URL_DL_8 = https://download.geofabrik.de/europe/france/champagne-ardenne-latest.osm.pbf   # URL for OSM DL
- ISO_code = FR_BL_test   # Enter the ISO 3166 code of the country of interest
- GEOM = 4.650609872346179 49.65060987234618 5.349390127653821 50.34939012765382   # Min/Max BoundingBox (minLong minLat maxLong maxLat)
- DestDataset_SHAPEFILE = $(FME_MF_DIR)output_serbia\aerialway   # Destination Esri Shapefile Folder
- DestDataset_SHAPEFILE_41 = $(FME_MF_DIR)output_serbia\aeroway   # Destination Esri Shapefile Folder
- DestDataset_SHAPEFILE_57 = $(FME_MF_DIR)output_serbia\boundary   # Destination Esri Shapefile Folder
- DestDataset_SHAPEFILE_37 = $(FME_MF_DIR)output_serbia\building   # Destination Esri Shapefile Folder
- DestDataset_SHAPEFILE_45 = $(FME_MF_DIR)output_serbia\place   # Destination Esri Shapefile Folder
- DestDataset_SHAPEFILE_53 = $(FME_MF_DIR)output_serbia\amenity   # Destination Esri Shapefile Folder
- DestDataset_SHAPEFILE_31 = $(FME_MF_DIR)output_serbia\barrier   # Destination Esri Shapefile Folder
- DestDataset_SHAPEFILE_35 = $(FME_MF_DIR)output_serbia\craft   # Destination Esri Shapefile Folder
- DestDataset_SHAPEFILE_39 = $(FME_MF_DIR)output_serbia\emergency   # Destination Esri Shapefile Folder
- DestDataset_SHAPEFILE_43 = $(FME_MF_DIR)output_serbia\historic   # Destination Esri Shapefile Folder
- DestDataset_SHAPEFILE_47 = $(FME_MF_DIR)output_serbia\geological   # Destination Esri Shapefile Folder
- DestDataset_SHAPEFILE_51 = $(FME_MF_DIR)output_serbia\landusel   # Destination Esri Shapefile Folder
- DestDataset_SHAPEFILE_55 = $(FME_MF_DIR)output_serbia\leisure   # Destination Esri Shapefile Folder
- DestDataset_SHAPEFILE_30 = $(FME_MF_DIR)output_serbia\man_made   # Destination Esri Shapefile Folder
- DestDataset_SHAPEFILE_32 = $(FME_MF_DIR)output_serbia\military   # Destination Esri Shapefile Folder
- DestDataset_SHAPEFILE_34 = $(FME_MF_DIR)output_serbia\natural   # Destination Esri Shapefile Folder
- DestDataset_SHAPEFILE_36 = $(FME_MF_DIR)output_serbia\office   # Destination Esri Shapefile Folder
- DestDataset_SHAPEFILE_38 = $(FME_MF_DIR)output_serbia\power   # Destination Esri Shapefile Folder
- DestDataset_SHAPEFILE_40 = $(FME_MF_DIR)output_serbia\public_transport   # Destination Esri Shapefile Folder
- DestDataset_SHAPEFILE_42 = $(FME_MF_DIR)output_serbia\railway   # Destination Esri Shapefile Folder
- DestDataset_SHAPEFILE_44 = $(FME_MF_DIR)output_serbia\route   # Destination Esri Shapefile Folder
- DestDataset_SHAPEFILE_46 = $(FME_MF_DIR)output_serbia\shop   # Destination Esri Shapefile Folder
- DestDataset_SHAPEFILE_48 = $(FME_MF_DIR)output_serbia\sport   # Destination Esri Shapefile Folder
- DestDataset_SHAPEFILE_50 = $(FME_MF_DIR)output_serbia\tourism   # Destination Esri Shapefile Folder
- DestDataset_SHAPEFILE_52 = $(FME_MF_DIR)output_serbia\waterway   # Destination Esri Shapefile Folder
- DestDataset_SHAPEFILE_54 = $(FME_MF_DIR)output_serbia\highway   # Destination Esri Shapefile Folder
- DestDataset_TEXTLINE = $(FME_MF_DIR)output_serbia\00_SUMMARY\summary_features.txt   # Destination Text File

Writers:
- SHAPEFILE_1: SHAPEFILE to $(FME_MF_DIR)output_serbia\aerialway
- SHAPEFILE_2: SHAPEFILE to $(FME_MF_DIR)output_tuvalu\Point
- SHAPEFILE_3: SHAPEFILE to $(DestDataset_SHAPEFILE_41)
- SHAPEFILE_4: SHAPEFILE to $(DestDataset_SHAPEFILE_57)
- SHAPEFILE_5: SHAPEFILE to $(DestDataset_SHAPEFILE_37)
- SHAPEFILE_6: SHAPEFILE to $(DestDataset_SHAPEFILE_45)
- SHAPEFILE_7: SHAPEFILE to $(DestDataset_SHAPEFILE)
- SHAPEFILE_8: SHAPEFILE to $(DestDataset_SHAPEFILE_53)
- SHAPEFILE_9: SHAPEFILE to $(DestDataset_SHAPEFILE_31)
- SHAPEFILE_10: SHAPEFILE to $(DestDataset_SHAPEFILE_35)
- SHAPEFILE_11: SHAPEFILE to $(DestDataset_SHAPEFILE_39)
- SHAPEFILE_12: SHAPEFILE to $(DestDataset_SHAPEFILE_43)
- SHAPEFILE_13: SHAPEFILE to $(DestDataset_SHAPEFILE_47)
- SHAPEFILE_14: SHAPEFILE to $(DestDataset_SHAPEFILE_51)
- SHAPEFILE_15: SHAPEFILE to $(DestDataset_SHAPEFILE_55)
- SHAPEFILE_16: SHAPEFILE to $(DestDataset_SHAPEFILE_30)
- SHAPEFILE_17: SHAPEFILE to $(DestDataset_SHAPEFILE_32)
- SHAPEFILE_18: SHAPEFILE to $(DestDataset_SHAPEFILE_34)
- SHAPEFILE_19: SHAPEFILE to $(DestDataset_SHAPEFILE_36)
- SHAPEFILE_20: SHAPEFILE to $(DestDataset_SHAPEFILE_38)
- SHAPEFILE_21: SHAPEFILE to $(DestDataset_SHAPEFILE_40)
- SHAPEFILE_22: SHAPEFILE to $(DestDataset_SHAPEFILE_42)
- SHAPEFILE_23: SHAPEFILE to $(DestDataset_SHAPEFILE_44)
- SHAPEFILE_24: SHAPEFILE to $(DestDataset_SHAPEFILE_46)
- SHAPEFILE_25: SHAPEFILE to $(DestDataset_SHAPEFILE_48)
- SHAPEFILE_26: SHAPEFILE to $(DestDataset_SHAPEFILE_50)
- SHAPEFILE_27: SHAPEFILE to $(DestDataset_SHAPEFILE_52)
- SHAPEFILE_28: SHAPEFILE to $(DestDataset_SHAPEFILE_54)
- TEXTLINE_1: TEXTLINE to $(DestDataset_TEXTLINE)

Creator
    COORDS = $(GEOM)
    COORDSYS = LL-WGS84
    GEOMTYPE = 2D Min/Max Box
    NUM = 1
    CREATED -> FeatureReader [INITIATOR]
    CREATED -> Tester
    CREATED -> Tester_2
    CREATED -> Tester_3
    CREATED -> Tester_4
    CREATED -> Tester_5
    CREATED -> Tester_6
    CREATED -> Tester_7
AttributeExposer
    ATTR_LIST = addr:housenumber,addr:street,admin_level,aerialway,aeroway,amenity,barrier,boundary,building,bus,craft,electrified,emergency,fire_hydrant:diameter,fire_hydrant:position,fire_hydrant:type,fme_geometry{0},fme_geometry{1},fme_geometry{2},fme_geometry{3},fme_geometry{4},gauge,geological,highway,historic,information,landuse,leisure,man_made,military,name,natural,network,office,place,power,public_transport,railway,ref,route,shop,source,sport,tourism,type,waterway,fme_feature_type,name:en,official_name,wikidata,according_to:CN,according_to:ES,according_to:IN,according_to:RS,according_to:RU,according_to:UA,according_to:XK
    -> GeometryFilter
GeometryFilter
    BREAK_AGG = No
    GEOM_PORT_NAMES = Collection Point Line Arc Area Ellipse Text Raster "Point Cloud" Surface Solid Null Instance
    POINT -> StatisticsCalculator
    POINT -> map_feature_classifier_2
    LINE -> map_feature_classifier_3
    LINE -> StatisticsCalculator
    AREA -> map_feature_classifier
    AREA -> StatisticsCalculator
map_feature_classifier_2: AttributeFilter
    ATTR_NAME = fme_feature_type
    ATTR_VALUES = <Empty>,<Missing>,<Null>,<Unfiltered>,aerialway,aeroway,amenity,barrier,boundary,building,craft,emergency,highway,historical,geological,landuse,leisure,man_made,military,natural,office,place,power,public_transport,railways,route,shop,sport,tourism,waterway
    aerialway -> blbla0000 (writer SHAPEFILE_7)
    aeroway -> Shapefile1000000 (writer SHAPEFILE_3)
    amenity -> Shapefile10000 (writer SHAPEFILE_8)
    barrier -> Shapefile10000 (writer SHAPEFILE_9)
    boundary -> Shapefile10000 (writer SHAPEFILE_4)
    building -> Shapefile10000 (writer SHAPEFILE_5)
    craft -> Shapefile10000 (writer SHAPEFILE_10)
    emergency -> Shapefile10000 (writer SHAPEFILE_11)
    highway -> Shapefile10000 (writer SHAPEFILE_28)
    historical -> Shapefile10000 (writer SHAPEFILE_12)
    geological -> sd0000 (writer SHAPEFILE_13)
    landuse -> Shapefile10000 (writer SHAPEFILE_14)
    leisure -> Shapefile10000 (writer SHAPEFILE_15)
    man_made -> Shapefile10000 (writer SHAPEFILE_16)
    military -> Shapefile10000 (writer SHAPEFILE_17)
    natural -> Shapefile10000 (writer SHAPEFILE_18)
    office -> Shapefile10000 (writer SHAPEFILE_19)
    place -> Shapefile10000 (writer SHAPEFILE_6)
    power -> Shapefile10000 (writer SHAPEFILE_20)
    public_transport -> Shapefile10000 (writer SHAPEFILE_21)
    railways -> Shapefile10000 (writer SHAPEFILE_22)
    route -> Shapefile10000 (writer SHAPEFILE_23)
    shop -> Shapefile10000 (writer SHAPEFILE_24)
    sport -> Shapefile10000 (writer SHAPEFILE_25)
    tourism -> Shapefile10000 (writer SHAPEFILE_26)
    waterway -> Shapefile10000 (writer SHAPEFILE_27)
map_feature_classifier_3: AttributeFilter
    ATTR_NAME = fme_feature_type
    ATTR_VALUES = <Empty>,<Missing>,<Null>,<Unfiltered>,aerialway,aeroway,amenity,barrier,boundary,building,craft,emergency,highway,historical,geological,landuse,leisure,man_made,military,natural,office,place,power,public_transport,railways,route,shop,sport,tourism,waterway
    aerialway -> blbla00 (writer SHAPEFILE_7)
    aeroway -> Shapefile10000 (writer SHAPEFILE_3)
    amenity -> Shapefile100 (writer SHAPEFILE_8)
    barrier -> Shapefile100 (writer SHAPEFILE_9)
    boundary -> Shapefile100 (writer SHAPEFILE_4)
    building -> Shapefile100 (writer SHAPEFILE_5)
    craft -> Shapefile100 (writer SHAPEFILE_10)
    emergency -> Shapefile100 (writer SHAPEFILE_11)
    highway -> Shapefile100 (writer SHAPEFILE_28)
    historical -> Shapefile100 (writer SHAPEFILE_12)
    geological -> sd00 (writer SHAPEFILE_13)
    landuse -> Shapefile100 (writer SHAPEFILE_14)
    leisure -> Shapefile100 (writer SHAPEFILE_15)
    man_made -> Shapefile100 (writer SHAPEFILE_16)
    military -> Shapefile100 (writer SHAPEFILE_17)
    natural -> Shapefile100 (writer SHAPEFILE_18)
    office -> Shapefile100 (writer SHAPEFILE_19)
    place -> Shapefile100 (writer SHAPEFILE_6)
    power -> Shapefile100 (writer SHAPEFILE_20)
    public_transport -> Shapefile100 (writer SHAPEFILE_21)
    railways -> Shapefile100 (writer SHAPEFILE_22)
    route -> Shapefile100 (writer SHAPEFILE_23)
    shop -> Shapefile100 (writer SHAPEFILE_24)
    sport -> Shapefile100 (writer SHAPEFILE_25)
    tourism -> Shapefile100 (writer SHAPEFILE_26)
    waterway -> Shapefile100 (writer SHAPEFILE_27)
map_feature_classifier: AttributeFilter
    ATTR_NAME = fme_feature_type
    ATTR_VALUES = <Empty>,<Missing>,<Null>,<Unfiltered>,aerialway,aeroway,amenity,barrier,boundary,building,craft,emergency,highway,historic,geological,landuse,leisure,man_made,military,natural,office,place,power,public_transport,railway,route,shop,sport,tourism,waterway
    aerialway -> blbla (writer SHAPEFILE_7)
    aeroway -> Shapefile100 (writer SHAPEFILE_3)
    amenity -> Shapefile1 (writer SHAPEFILE_8)
    barrier -> Shapefile1 (writer SHAPEFILE_9)
    boundary -> Shapefile1 (writer SHAPEFILE_4)
    building -> Shapefile1 (writer SHAPEFILE_5)
    craft -> Shapefile1 (writer SHAPEFILE_10)
    emergency -> Shapefile1 (writer SHAPEFILE_11)
    highway -> Shapefile1 (writer SHAPEFILE_28)
    historic -> Shapefile1 (writer SHAPEFILE_12)
    geological -> sd (writer SHAPEFILE_13)
    landuse -> Shapefile1 (writer SHAPEFILE_14)
    leisure -> Shapefile1 (writer SHAPEFILE_15)
    man_made -> Shapefile1 (writer SHAPEFILE_16)
    military -> Shapefile1 (writer SHAPEFILE_17)
    natural -> Shapefile1 (writer SHAPEFILE_18)
    office -> Shapefile1 (writer SHAPEFILE_19)
    place -> Shapefile1 (writer SHAPEFILE_6)
    power -> Shapefile1 (writer SHAPEFILE_20)
    public_transport -> Shapefile1 (writer SHAPEFILE_21)
    railway -> Shapefile1 (writer SHAPEFILE_22)
    route -> Shapefile1 (writer SHAPEFILE_23)
    shop -> Shapefile1 (writer SHAPEFILE_24)
    sport -> Shapefile1 (writer SHAPEFILE_25)
    tourism -> Shapefile1 (writer SHAPEFILE_26)
    waterway -> Shapefile1 (writer SHAPEFILE_27)

Bookmark: Data Download
FeatureReader
    ATTR_ACCUM_MODE = Only Use Result
    COMBINE_GEOM = Use Result
    DATASET = $(URL_DL_1)
    FEATURETYPES = $(FEATURETYPES)
    FORMAT = OSMPBF
    INTERACT = Initiator Intersects Result
    OSMPBF_COMMUNITY_FEATURE_TYPES = MAPPED
    OSMPBF_HANDLE_MULTI = SELECT_FIRST
    OSMPBF_KEY_SCHEMA_MODE = EXCLUDE_KEYVAL_SCHEMAS
    OSMPBF_QUERY_FEATURE_TYPES_FOR_MERGE_FILTERS = Yes
    OSMPBF_READ_BOOLEANS_AS_YES_NO = YES
    OSMPBF_READ_NULLS = YES
    OSMPBF_USER_CONFIG = NO
    OSMPBF_USE_FAST_NODE_INDEX = Yes
    OSMPBF_USE_SEARCH_ENVELOPE = NO
    OUTPUT_FEATURES_DISPLAY = Schema and Data Features
    <OTHER> -> AttributeExposer
Tester_7
    BOOL_OP = COMPOSITE
    COMPOSITE_TEST = 1 AND 2 AND 3 AND 4 AND 5 AND 6 AND 7 AND 8 AND 9 AND 10 AND 11 AND 12 AND 13 AND 14 AND 15 AND 16 AND 17 AND 18 AND 19 AND 20 AND 21 AND 22 AND 23 AND 24 AND 25 AND 26 AND 27 AND 28
    TEST_CLAUSE:
      TEST $(URL_DL_1) != $(URL_DL_2)
      TEST $(URL_DL_1) != $(URL_DL_3)
      TEST $(URL_DL_1) != $(URL_DL_4)
      TEST $(URL_DL_1) != $(URL_DL_5)
      TEST $(URL_DL_1) != $(URL_DL_6)
      TEST $(URL_DL_1) != $(URL_DL_7)
      TEST $(URL_DL_1) != $(URL_DL_8)
      TEST $(URL_DL_2) != $(URL_DL_3)
      TEST $(URL_DL_2) != $(URL_DL_4)
      TEST $(URL_DL_2) != $(URL_DL_5)
      TEST $(URL_DL_2) != $(URL_DL_6)
      TEST $(URL_DL_2) != $(URL_DL_7)
      TEST $(URL_DL_2) != $(URL_DL_8)
      TEST $(URL_DL_3) != $(URL_DL_4)
      TEST $(URL_DL_3) != $(URL_DL_5)
      TEST $(URL_DL_3) != $(URL_DL_6)
      TEST $(URL_DL_3) != $(URL_DL_7)
      TEST $(URL_DL_3) != $(URL_DL_8)
      TEST $(URL_DL_4) != $(URL_DL_5)
      TEST $(URL_DL_4) != $(URL_DL_6)
      TEST $(URL_DL_4) != $(URL_DL_7)
      TEST $(URL_DL_4) != $(URL_DL_8)
      TEST $(URL_DL_5) != $(URL_DL_6)
      TEST $(URL_DL_5) != $(URL_DL_7)
      TEST $(URL_DL_5) != $(URL_DL_8)
      TEST $(URL_DL_6) != $(URL_DL_7)
      TEST $(URL_DL_6) != $(URL_DL_8)
      TEST $(URL_DL_7) != $(URL_DL_8)
    TEST_MODE = TEST
    PASSED -> FeatureReader_8 [INITIATOR]
FeatureReader_8
    ATTR_ACCUM_MODE = Only Use Result
    COMBINE_GEOM = Use Result
    DATASET = $(URL_DL_8)
    FEATURETYPES = $(FEATURETYPES)
    FORMAT = OSMPBF
    INTERACT = Initiator Intersects Result
    OSMPBF_COMMUNITY_FEATURE_TYPES = MAPPED
    OSMPBF_HANDLE_MULTI = SELECT_FIRST
    OSMPBF_KEY_SCHEMA_MODE = EXCLUDE_KEYVAL_SCHEMAS
    OSMPBF_QUERY_FEATURE_TYPES_FOR_MERGE_FILTERS = Yes
    OSMPBF_READ_BOOLEANS_AS_YES_NO = YES
    OSMPBF_READ_NULLS = YES
    OSMPBF_USER_CONFIG = NO
    OSMPBF_USE_FAST_NODE_INDEX = Yes
    OSMPBF_USE_SEARCH_ENVELOPE = NO
    OUTPUT_FEATURES_DISPLAY = Schema and Data Features
    <OTHER> -> AttributeExposer
Tester_6
    BOOL_OP = COMPOSITE
    COMPOSITE_TEST = 1 AND 2 AND 3 AND 4 AND 5 AND 6 AND 7 AND 8 AND 9 AND 10 AND 11 AND 12 AND 13 AND 14 AND 15 AND 16 AND 17 AND 18 AND 19 AND 20 AND 21
    TEST_CLAUSE:
      TEST $(URL_DL_1) != $(URL_DL_2)
      TEST $(URL_DL_1) != $(URL_DL_3)
      TEST $(URL_DL_1) != $(URL_DL_4)
      TEST $(URL_DL_1) != $(URL_DL_5)
      TEST $(URL_DL_1) != $(URL_DL_6)
      TEST $(URL_DL_1) != $(URL_DL_7)
      TEST $(URL_DL_2) != $(URL_DL_3)
      TEST $(URL_DL_2) != $(URL_DL_4)
      TEST $(URL_DL_2) != $(URL_DL_5)
      TEST $(URL_DL_2) != $(URL_DL_6)
      TEST $(URL_DL_2) != $(URL_DL_7)
      TEST $(URL_DL_3) != $(URL_DL_4)
      TEST $(URL_DL_3) != $(URL_DL_5)
      TEST $(URL_DL_3) != $(URL_DL_6)
      TEST $(URL_DL_3) != $(URL_DL_7)
      TEST $(URL_DL_4) != $(URL_DL_5)
      TEST $(URL_DL_4) != $(URL_DL_6)
      TEST $(URL_DL_4) != $(URL_DL_7)
      TEST $(URL_DL_5) != $(URL_DL_6)
      TEST $(URL_DL_5) != $(URL_DL_7)
      TEST $(URL_DL_6) != $(URL_DL_7)
    TEST_MODE = TEST
    PASSED -> FeatureReader_7 [INITIATOR]
FeatureReader_7
    ATTR_ACCUM_MODE = Only Use Result
    COMBINE_GEOM = Use Result
    DATASET = $(URL_DL_7)
    FEATURETYPES = $(FEATURETYPES)
    FORMAT = OSMPBF
    INTERACT = Initiator Intersects Result
    OSMPBF_COMMUNITY_FEATURE_TYPES = MAPPED
    OSMPBF_HANDLE_MULTI = SELECT_FIRST
    OSMPBF_KEY_SCHEMA_MODE = EXCLUDE_KEYVAL_SCHEMAS
    OSMPBF_QUERY_FEATURE_TYPES_FOR_MERGE_FILTERS = Yes
    OSMPBF_READ_BOOLEANS_AS_YES_NO = YES
    OSMPBF_READ_NULLS = YES
    OSMPBF_USER_CONFIG = NO
    OSMPBF_USE_FAST_NODE_INDEX = Yes
    OSMPBF_USE_SEARCH_ENVELOPE = NO
    OUTPUT_FEATURES_DISPLAY = Schema and Data Features
    <OTHER> -> AttributeExposer
Tester_5
    BOOL_OP = COMPOSITE
    COMPOSITE_TEST = 1 AND 2 AND 3 AND 4 AND 5 AND 6 AND 7 AND 8 AND 9 AND 10 AND 11 AND 12 AND 13 AND 14 AND 15
    TEST_CLAUSE:
      TEST $(URL_DL_1) != $(URL_DL_2)
      TEST $(URL_DL_1) != $(URL_DL_3)
      TEST $(URL_DL_1) != $(URL_DL_4)
      TEST $(URL_DL_1) != $(URL_DL_5)
      TEST $(URL_DL_1) != $(URL_DL_6)
      TEST $(URL_DL_2) != $(URL_DL_3)
      TEST $(URL_DL_2) != $(URL_DL_4)
      TEST $(URL_DL_2) != $(URL_DL_5)
      TEST $(URL_DL_2) != $(URL_DL_6)
      TEST $(URL_DL_3) != $(URL_DL_4)
      TEST $(URL_DL_3) != $(URL_DL_5)
      TEST $(URL_DL_3) != $(URL_DL_6)
      TEST $(URL_DL_4) != $(URL_DL_5)
      TEST $(URL_DL_4) != $(URL_DL_6)
      TEST $(URL_DL_5) != $(URL_DL_6)
    TEST_MODE = TEST
    PASSED -> FeatureReader_6 [INITIATOR]
FeatureReader_6
    ATTR_ACCUM_MODE = Only Use Result
    COMBINE_GEOM = Use Result
    DATASET = $(URL_DL_6)
    FEATURETYPES = $(FEATURETYPES)
    FORMAT = OSMPBF
    INTERACT = Initiator Intersects Result
    OSMPBF_COMMUNITY_FEATURE_TYPES = MAPPED
    OSMPBF_HANDLE_MULTI = SELECT_FIRST
    OSMPBF_KEY_SCHEMA_MODE = EXCLUDE_KEYVAL_SCHEMAS
    OSMPBF_QUERY_FEATURE_TYPES_FOR_MERGE_FILTERS = Yes
    OSMPBF_READ_BOOLEANS_AS_YES_NO = YES
    OSMPBF_READ_NULLS = YES
    OSMPBF_USER_CONFIG = NO
    OSMPBF_USE_FAST_NODE_INDEX = Yes
    OSMPBF_USE_SEARCH_ENVELOPE = NO
    OUTPUT_FEATURES_DISPLAY = Schema and Data Features
    <OTHER> -> AttributeExposer
Tester_4
    BOOL_OP = AND
    COMPOSITE_TEST = 1 AND 2 AND 3 AND 4 AND 5 AND 6 AND 7 AND 8 AND 9 AND 10
    TEST_CLAUSE:
      TEST $(URL_DL_1) != $(URL_DL_2)
      TEST $(URL_DL_1) != $(URL_DL_3)
      TEST $(URL_DL_1) != $(URL_DL_4)
      TEST $(URL_DL_1) != $(URL_DL_5)
      TEST $(URL_DL_2) != $(URL_DL_3)
      TEST $(URL_DL_2) != $(URL_DL_4)
      TEST $(URL_DL_2) != $(URL_DL_5)
      TEST $(URL_DL_3) != $(URL_DL_4)
      TEST $(URL_DL_3) != $(URL_DL_5)
      TEST $(URL_DL_4) != $(URL_DL_5)
    TEST_MODE = TEST
    PASSED -> FeatureReader_5 [INITIATOR]
FeatureReader_5
    ATTR_ACCUM_MODE = Only Use Result
    COMBINE_GEOM = Use Result
    DATASET = $(URL_DL_5)
    FEATURETYPES = $(FEATURETYPES)
    FORMAT = OSMPBF
    INTERACT = Initiator Intersects Result
    OSMPBF_COMMUNITY_FEATURE_TYPES = MAPPED
    OSMPBF_HANDLE_MULTI = SELECT_FIRST
    OSMPBF_KEY_SCHEMA_MODE = EXCLUDE_KEYVAL_SCHEMAS
    OSMPBF_QUERY_FEATURE_TYPES_FOR_MERGE_FILTERS = Yes
    OSMPBF_READ_BOOLEANS_AS_YES_NO = YES
    OSMPBF_READ_NULLS = YES
    OSMPBF_USER_CONFIG = NO
    OSMPBF_USE_FAST_NODE_INDEX = Yes
    OSMPBF_USE_SEARCH_ENVELOPE = NO
    OUTPUT_FEATURES_DISPLAY = Schema and Data Features
    <OTHER> -> AttributeExposer
Tester_3
    BOOL_OP = AND
    COMPOSITE_TEST = 1 AND 2 AND 3 AND 4 AND 5 AND 6
    TEST_CLAUSE:
      TEST $(URL_DL_1) != $(URL_DL_2)
      TEST $(URL_DL_1) != $(URL_DL_3)
      TEST $(URL_DL_1) != $(URL_DL_4)
      TEST $(URL_DL_2) != $(URL_DL_3)
      TEST $(URL_DL_2) != $(URL_DL_4)
      TEST $(URL_DL_3) != $(URL_DL_4)
    TEST_MODE = TEST
    PASSED -> FeatureReader_4 [INITIATOR]
FeatureReader_4
    ATTR_ACCUM_MODE = Only Use Result
    COMBINE_GEOM = Use Result
    DATASET = $(URL_DL_4)
    FEATURETYPES = $(FEATURETYPES)
    FORMAT = OSMPBF
    INTERACT = Initiator Intersects Result
    OSMPBF_COMMUNITY_FEATURE_TYPES = MAPPED
    OSMPBF_HANDLE_MULTI = SELECT_FIRST
    OSMPBF_KEY_SCHEMA_MODE = EXCLUDE_KEYVAL_SCHEMAS
    OSMPBF_QUERY_FEATURE_TYPES_FOR_MERGE_FILTERS = Yes
    OSMPBF_READ_BOOLEANS_AS_YES_NO = YES
    OSMPBF_READ_NULLS = YES
    OSMPBF_USER_CONFIG = NO
    OSMPBF_USE_FAST_NODE_INDEX = Yes
    OSMPBF_USE_SEARCH_ENVELOPE = NO
    OUTPUT_FEATURES_DISPLAY = Schema and Data Features
    <OTHER> -> AttributeExposer
Tester_2
    BOOL_OP = AND
    COMPOSITE_TEST = 1 AND 2 AND 3
    TEST_CLAUSE:
      TEST $(URL_DL_1) != $(URL_DL_2)
      TEST $(URL_DL_2) != $(URL_DL_3)
      TEST $(URL_DL_1) != $(URL_DL_3)
    TEST_MODE = TEST
    PASSED -> FeatureReader_3 [INITIATOR]
FeatureReader_3
    ATTR_ACCUM_MODE = Only Use Result
    COMBINE_GEOM = Use Result
    DATASET = $(URL_DL_3)
    FEATURETYPES = $(FEATURETYPES)
    FORMAT = OSMPBF
    INTERACT = Initiator Intersects Result
    OSMPBF_COMMUNITY_FEATURE_TYPES = MAPPED
    OSMPBF_HANDLE_MULTI = SELECT_FIRST
    OSMPBF_KEY_SCHEMA_MODE = EXCLUDE_KEYVAL_SCHEMAS
    OSMPBF_QUERY_FEATURE_TYPES_FOR_MERGE_FILTERS = Yes
    OSMPBF_READ_BOOLEANS_AS_YES_NO = YES
    OSMPBF_READ_NULLS = YES
    OSMPBF_USER_CONFIG = NO
    OSMPBF_USE_FAST_NODE_INDEX = Yes
    OSMPBF_USE_SEARCH_ENVELOPE = NO
    OUTPUT_FEATURES_DISPLAY = Schema and Data Features
    <OTHER> -> AttributeExposer
Tester
    BOOL_OP = OR
    COMPOSITE_TEST = 1
    TEST_CLAUSE = TEST $(URL_DL_1) != $(URL_DL_2)
    TEST_MODE = TEST
    PASSED -> FeatureReader_2 [INITIATOR]
FeatureReader_2
    ATTR_ACCUM_MODE = Only Use Result
    COMBINE_GEOM = Use Result
    DATASET = $(URL_DL_2)
    FEATURETYPES = $(FEATURETYPES)
    FORMAT = OSMPBF
    INTERACT = Initiator Intersects Result
    OSMPBF_COMMUNITY_FEATURE_TYPES = MAPPED
    OSMPBF_HANDLE_MULTI = SELECT_FIRST
    OSMPBF_KEY_SCHEMA_MODE = EXCLUDE_KEYVAL_SCHEMAS
    OSMPBF_QUERY_FEATURE_TYPES_FOR_MERGE_FILTERS = Yes
    OSMPBF_READ_BOOLEANS_AS_YES_NO = YES
    OSMPBF_READ_NULLS = YES
    OSMPBF_USER_CONFIG = NO
    OSMPBF_USE_FAST_NODE_INDEX = Yes
    OSMPBF_USE_SEARCH_ENVELOPE = NO
    OUTPUT_FEATURES_DISPLAY = Schema and Data Features
    <OTHER> -> AttributeExposer

Bookmark: Log/statistics
StatisticsCalculator
    CALCULATION_MODE = NUMERIC
    FEAT_STATS = fme_feature_type,NUMERIC_MODE,,,COUNT,,,,,,,,,
    GROUP_BY = fme_feature_type
    SUMMARY -> AttributeManager
AttributeManager
    ATTR_TABLE = SET_TO text_line_data = @Value(fme_feature_type) : @Value(fme_feature_type.total_count) features
    -> text_line (writer TEXTLINE_1)
text_line (writer TEXTLINE_1)
    attributes: text_line_data buffer

Bookmark: Writers line
Shapefile10000 (writer SHAPEFILE_27)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile10000 (writer SHAPEFILE_26)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile10000 (writer SHAPEFILE_25)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile10000 (writer SHAPEFILE_24)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile10000 (writer SHAPEFILE_23)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile10000 (writer SHAPEFILE_22)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile10000 (writer SHAPEFILE_21)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile10000 (writer SHAPEFILE_20)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile10000 (writer SHAPEFILE_6)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile10000 (writer SHAPEFILE_19)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile10000 (writer SHAPEFILE_18)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile10000 (writer SHAPEFILE_17)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile10000 (writer SHAPEFILE_16)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile10000 (writer SHAPEFILE_15)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile10000 (writer SHAPEFILE_14)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
sd0000 (writer SHAPEFILE_13)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile10000 (writer SHAPEFILE_12)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile10000 (writer SHAPEFILE_28)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile10000 (writer SHAPEFILE_11)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile10000 (writer SHAPEFILE_10)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile10000 (writer SHAPEFILE_5)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile10000 (writer SHAPEFILE_4)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile10000 (writer SHAPEFILE_9)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile10000 (writer SHAPEFILE_8)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile1000000 (writer SHAPEFILE_3)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
blbla0000 (writer SHAPEFILE_7)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)

Bookmark: Writers line
Shapefile100 (writer SHAPEFILE_27)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile100 (writer SHAPEFILE_26)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile100 (writer SHAPEFILE_25)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile100 (writer SHAPEFILE_24)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile100 (writer SHAPEFILE_23)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile100 (writer SHAPEFILE_22)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile100 (writer SHAPEFILE_21)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile100 (writer SHAPEFILE_20)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile100 (writer SHAPEFILE_6)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile100 (writer SHAPEFILE_19)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile100 (writer SHAPEFILE_18)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile100 (writer SHAPEFILE_17)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile100 (writer SHAPEFILE_16)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile100 (writer SHAPEFILE_15)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile100 (writer SHAPEFILE_14)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
sd00 (writer SHAPEFILE_13)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile100 (writer SHAPEFILE_12)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile100 (writer SHAPEFILE_28)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile100 (writer SHAPEFILE_11)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile100 (writer SHAPEFILE_10)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile100 (writer SHAPEFILE_5)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile100 (writer SHAPEFILE_4)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile100 (writer SHAPEFILE_9)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile100 (writer SHAPEFILE_8)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile10000 (writer SHAPEFILE_3)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
blbla00 (writer SHAPEFILE_7)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)

Bookmark: Writers polygone
Shapefile1 (writer SHAPEFILE_27)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile1 (writer SHAPEFILE_26)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile1 (writer SHAPEFILE_25)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile1 (writer SHAPEFILE_24)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile1 (writer SHAPEFILE_23)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile1 (writer SHAPEFILE_22)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile1 (writer SHAPEFILE_21)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile1 (writer SHAPEFILE_20)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile1 (writer SHAPEFILE_6)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile1 (writer SHAPEFILE_19)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile1 (writer SHAPEFILE_18)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile1 (writer SHAPEFILE_17)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile1 (writer SHAPEFILE_16)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile1 (writer SHAPEFILE_15)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile1 (writer SHAPEFILE_14)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
sd (writer SHAPEFILE_13)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile1 (writer SHAPEFILE_12)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile1 (writer SHAPEFILE_28)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile1 (writer SHAPEFILE_11)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile1 (writer SHAPEFILE_10)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile1 (writer SHAPEFILE_5)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile1 (writer SHAPEFILE_4)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile1 (writer SHAPEFILE_9)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile1 (writer SHAPEFILE_8)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
Shapefile100 (writer SHAPEFILE_3)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
blbla (writer SHAPEFILE_7)
    attributes: addr:house char(200), addr:stree char(200), admin_leve char(200), aerialway char(200), aeroway char(200), amenity char(200), barrier char(200), boundary char(200), building char(200), bus char(200), craft char(200), electrifie char(200), emergency char(200), fire_hydra char(200), fire_hyd00 char(200), fire_hyd01 char(200), fme_geomet char(200), fme_geom00 char(200), fme_geom01 char(200), fme_geom02 char(200), fme_geom03 char(200), gauge char(200), geological char(200), highway char(200), historic char(200), informatio char(200), landuse char(200), leisure char(200), man_made char(200), military char(200),
      name char(200), natural char(200), network char(200), office char(200), place char(200), power char(200), public_tra char(200), railway char(200), ref char(200), route char(200), shop char(200), source char(200), sport char(200), tourism char(200), type char(200), waterway char(200), name:en char(200), official_n char(200), wikidata char(200), according_ char(200), accordin00 char(200), accordin01 char(200), accordin02 char(200), accordin03 char(200), accordin04 char(200), accordin05 char(200)
