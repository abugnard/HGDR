FME workspace DEM_geotiff2geotiff.fmw

Parameters:
- DestDataset_GEOTIFF = $(FME_MF_DIR)output_DEM   # Destination GeoTIFF Folder
- GEOM_minLON = 6.2383359331190205   # Minimum Longitude
- GEOM_minLAT = 45.79725436314601   # Minimum Latitude
- GEOM_maxLAT = 47.10108221883745   # Maximum Latitude
- GEOM_maxLON = 7.542163788810462   # Maximum Longitude
- ISO_code = test6   # ISO2 of the country

Writers:
- GEOTIFF_1: GEOTIFF to $(DestDataset_GEOTIFF)

Creator_2
    COORDSYS = LL-WGS84
    GEOMTYPE = Geometry Object
    NUM = 1
    CREATED -> N10E30
    CREATED -> N10E0
    CREATED -> N10W30
    CREATED -> N10E60
    CREATED -> N10E90
    CREATED -> N10E120
    CREATED -> N10E150
    CREATED -> N10W60
    CREATED -> N10W120
    CREATED -> N10W90
    CREATED -> N10W150
    CREATED -> N10W180
    CREATED -> N30W30
    CREATED -> N30W60
    CREATED -> N30W90
    CREATED -> N30W120
    CREATED -> N30W150
    CREATED -> N30W180
    CREATED -> N30E150
    CREATED -> N30E120
    CREATED -> N30E90
    CREATED -> N30E60
    CREATED -> N30E30
    CREATED -> N30E0
    CREATED -> N50E0
    CREATED -> N50E30
    CREATED -> N50E60
    CREATED -> N50E90
    CREATED -> N50E120
    CREATED -> N50E150
    CREATED -> N50W180
    CREATED -> N50W150
    CREATED -> N50W120
    CREATED -> N50W90
    CREATED -> N50W60
    CREATED -> N50W30
    CREATED -> N70W30
    CREATED -> N70W60
    CREATED -> N70W90
    CREATED -> N70W120
    CREATED -> N70W150
    CREATED -> N70W180
    CREATED -> N70E150
    CREATED -> N70E120
    CREATED -> N70E90
    CREATED -> N70E60
    CREATED -> N70E30
    CREATED -> N70E0
    CREATED -> S10E0
    CREATED -> S10E30
    CREATED -> S10E60
    CREATED -> S10E90
    CREATED -> S10E120
    CREATED -> S10E150
    CREATED -> S10W30
    CREATED -> S10W60
    CREATED -> S10W90
    CREATED -> S10W120
    CREATED -> S10W150
    CREATED -> S10W180
    CREATED -> S30E0
    CREATED -> S30E30
    CREATED -> S30E60
    CREATED -> S30E90
    CREATED -> S30E120
    CREATED -> S30E150
    CREATED -> S30W30
    CREATED -> S30W60
    CREATED -> S30W90
    CREATED -> S30W120
    CREATED -> S30W150
    CREATED -> S30W180
    CREATED -> S50E0
    CREATED -> S50E30
    CREATED -> S50E60
    CREATED -> S50E90
    CREATED -> S50E120
    CREATED -> S50E150
    CREATED -> S50W30
    CREATED -> S50W60
    CREATED -> S50W90
    CREATED -> S50W120
    CREATED -> S50W150
    CREATED -> S50W180
    CREATED -> S70E0
    CREATED -> S70E30
    CREATED -> S70E60
    CREATED -> S70E90
    CREATED -> S70E120
    CREATED -> S70E150
    CREATED -> S70W30
    CREATED -> S70W60
    CREATED -> S70W90
    CREATED -> S70W120
    CREATED -> S70W150
    CREATED -> S70W180
    CREATED -> S90E0
    CREATED -> S90E30
    CREATED -> S90E60
    CREATED -> S90E90
    CREATED -> S90E120
    CREATED -> S90E150
    CREATED -> S90W30
    CREATED -> S90W60
    CREATED -> 90W90
    CREATED -> S90W120
    CREATED -> S90W150
    CREATED -> S90W180
N70E0: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [70,90]
      NUM_TEST $(GEOM_maxLON) RANGE [0,30]
      NUM_TEST $(GEOM_maxLAT) RANGE [70,90]
      NUM_TEST $(GEOM_minLON) RANGE [0,30]
      NUM_TEST $(GEOM_minLAT) RANGE [70,90]
      NUM_TEST $(GEOM_minLON) RANGE [0,30]
      NUM_TEST $(GEOM_minLAT) RANGE [70,90]
      NUM_TEST $(GEOM_maxLON) RANGE [0,30]",<pass>
    <pass> -> FeatureReader_38 [INITIATOR]
FeatureReader_38
    ATTRIBUTES = TIFF,
    ATTR_ACCUM_MODE = Only Use Result
    COMBINE_GEOM = Use Result
    COORDSYS = LL-WGS84
    DATASET = $(FME_MF_DIR_ENCODED)DEM\N70\70n000e_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
N70E30: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [70,90]
      NUM_TEST $(GEOM_maxLON) RANGE [30,60]
      NUM_TEST $(GEOM_maxLAT) RANGE [70,90]
      NUM_TEST $(GEOM_minLON) RANGE [30,60]
      NUM_TEST $(GEOM_minLAT) RANGE [70,90]
      NUM_TEST $(GEOM_minLON) RANGE [30,60]
      NUM_TEST $(GEOM_minLAT) RANGE [70,90]
      NUM_TEST $(GEOM_maxLON) RANGE [30,60]",<pass>
    <pass> -> FeatureReader_37 [INITIATOR]
FeatureReader_37
    ATTRIBUTES = TIFF,
    ATTR_ACCUM_MODE = Only Use Result
    COMBINE_GEOM = Use Result
    DATASET = $(FME_MF_DIR_ENCODED)DEM\N70\70n030e_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
N70E60: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [70,90]
      NUM_TEST $(GEOM_maxLON) RANGE [60,90]
      NUM_TEST $(GEOM_maxLAT) RANGE [70,90]
      NUM_TEST $(GEOM_minLON) RANGE [60,90]
      NUM_TEST $(GEOM_minLAT) RANGE [70,90]
      NUM_TEST $(GEOM_minLON) RANGE [60,90]
      NUM_TEST $(GEOM_minLAT) RANGE [70,90]
      NUM_TEST $(GEOM_maxLON) RANGE [60,90]",<pass>
    <pass> -> FeatureReader_40 [INITIATOR]
FeatureReader_40
    ATTRIBUTES = TIFF,
    ATTR_ACCUM_MODE = Only Use Result
    COMBINE_GEOM = Use Result
    COORDSYS = LL-WGS84
    DATASET = $(FME_MF_DIR_ENCODED)DEM\N70\70N060E_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
N70E90: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [70,90]
      NUM_TEST $(GEOM_maxLON) RANGE [90,120]
      NUM_TEST $(GEOM_maxLAT) RANGE [70,90]
      NUM_TEST $(GEOM_minLON) RANGE [90,120]
      NUM_TEST $(GEOM_minLAT) RANGE [70,90]
      NUM_TEST $(GEOM_minLON) RANGE [90,120]
      NUM_TEST $(GEOM_minLAT) RANGE [70,90]
      NUM_TEST $(GEOM_maxLON) RANGE [90,120]",<pass>
    <pass> -> FeatureReader_41 [INITIATOR]
FeatureReader_41
    ATTRIBUTES = TIFF,
    ATTR_ACCUM_MODE = Only Use Result
    COMBINE_GEOM = Use Result
    COORDSYS = LL-WGS84
    DATASET = $(FME_MF_DIR_ENCODED)DEM\N70\70N090E_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
N70E120: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [70,90]
      NUM_TEST $(GEOM_maxLON) RANGE [120,150]
      NUM_TEST $(GEOM_maxLAT) RANGE [70,90]
      NUM_TEST $(GEOM_minLON) RANGE [120,150]
      NUM_TEST $(GEOM_minLAT) RANGE [70,90]
      NUM_TEST $(GEOM_minLON) RANGE [120,150]
      NUM_TEST $(GEOM_minLAT) RANGE [70,90]
      NUM_TEST $(GEOM_maxLON) RANGE [120,150]",<pass>
    <pass> -> FeatureReader_42 [INITIATOR]
FeatureReader_42
    ATTRIBUTES = TIFF,
    ATTR_ACCUM_MODE = Only Use Result
    COMBINE_GEOM = Use Result
    COORDSYS = LL-WGS84
    DATASET = $(FME_MF_DIR_ENCODED)DEM\N70\70n120e_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
N70E150: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [70,90]
      NUM_TEST $(GEOM_maxLON) RANGE [150,180]
      NUM_TEST $(GEOM_maxLAT) RANGE [70,90]
      NUM_TEST $(GEOM_minLON) RANGE [150,180]
      NUM_TEST $(GEOM_minLAT) RANGE [70,90]
      NUM_TEST $(GEOM_minLON) RANGE [150,180]
      NUM_TEST $(GEOM_minLAT) RANGE [70,90]
      NUM_TEST $(GEOM_maxLON) RANGE [150,180]",<pass>
    <pass> -> FeatureReader_43 [INITIATOR]
FeatureReader_43
    ATTRIBUTES = TIFF,
    ATTR_ACCUM_MODE = Only Use Result
    COMBINE_GEOM = Use Result
    COORDSYS = LL-WGS84
    DATASET = $(FME_MF_DIR_ENCODED)DEM\N70\70n150e_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
N70W180: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [70,90]
      NUM_TEST $(GEOM_maxLON) RANGE [-180,-150]
      NUM_TEST $(GEOM_maxLAT) RANGE [70,90]
      NUM_TEST $(GEOM_minLON) RANGE [-180,-150]
      NUM_TEST $(GEOM_minLAT) RANGE [70,90]
      NUM_TEST $(GEOM_minLON) RANGE [-180,-150]
      NUM_TEST $(GEOM_minLAT) RANGE [70,90]
      NUM_TEST $(GEOM_maxLON) RANGE [-180,-150]",<pass>
    <pass> -> FeatureReader_48 [INITIATOR]
FeatureReader_48
    ATTRIBUTES = TIFF,
    ATTR_ACCUM_MODE = Only Use Result
    COMBINE_GEOM = Use Result
    COORDSYS = LL-WGS84
    DATASET = $(FME_MF_DIR_ENCODED)DEM\N70\70n180w_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
N70W150: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [70,90]
      NUM_TEST $(GEOM_maxLON) RANGE [-150,-120]
      NUM_TEST $(GEOM_maxLAT) RANGE [70,90]
      NUM_TEST $(GEOM_minLON) RANGE [-150,-120]
      NUM_TEST $(GEOM_minLAT) RANGE [70,90]
      NUM_TEST $(GEOM_minLON) RANGE [-150,-120]
      NUM_TEST $(GEOM_minLAT) RANGE [70,90]
      NUM_TEST $(GEOM_maxLON) RANGE [-150,-120]",<pass>
    <pass> -> FeatureReader_47 [INITIATOR]
FeatureReader_47
    ATTRIBUTES = TIFF,
    ATTR_ACCUM_MODE = Only Use Result
    COMBINE_GEOM = Use Result
    COORDSYS = LL-WGS84
    DATASET = $(FME_MF_DIR_ENCODED)DEM\N70\70n150w_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
N70W120: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [70,90]
      NUM_TEST $(GEOM_maxLON) RANGE [-120,-90]
      NUM_TEST $(GEOM_maxLAT) RANGE [70,90]
      NUM_TEST $(GEOM_minLON) RANGE [-120,-90]
      NUM_TEST $(GEOM_minLAT) RANGE [70,90]
      NUM_TEST $(GEOM_minLON) RANGE [-120,-90]
      NUM_TEST $(GEOM_minLAT) RANGE [70,90]
      NUM_TEST $(GEOM_maxLON) RANGE [-120,-90]",<pass>
    <pass> -> FeatureReader_46 [INITIATOR]
FeatureReader_46
    ATTRIBUTES = TIFF,
    ATTR_ACCUM_MODE = Only Use Result
    COMBINE_GEOM = Use Result
    COORDSYS = LL-WGS84
    DATASET = $(FME_MF_DIR_ENCODED)DEM\N70\70n120w_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
N70W90: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [70,90]
      NUM_TEST $(GEOM_maxLON) RANGE [-90,-60]
      NUM_TEST $(GEOM_maxLAT) RANGE [70,90]
      NUM_TEST $(GEOM_minLON) RANGE [-90,-60]
      NUM_TEST $(GEOM_minLAT) RANGE [70,90]
      NUM_TEST $(GEOM_minLON) RANGE [-90,-60]
      NUM_TEST $(GEOM_minLAT) RANGE [70,90]
      NUM_TEST $(GEOM_maxLON) RANGE [-90,-60]",<pass>
    <pass> -> FeatureReader_45 [INITIATOR]
FeatureReader_45
    ATTRIBUTES = TIFF,
    ATTR_ACCUM_MODE = Only Use Result
    COMBINE_GEOM = Use Result
    COORDSYS = LL-WGS84
    DATASET = $(FME_MF_DIR_ENCODED)DEM\N70\70n090w_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
N70W60: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [70,90]
      NUM_TEST $(GEOM_maxLON) RANGE [-60,-30]
      NUM_TEST $(GEOM_maxLAT) RANGE [70,90]
      NUM_TEST $(GEOM_minLON) RANGE [-60,-30]
      NUM_TEST $(GEOM_minLAT) RANGE [70,90]
      NUM_TEST $(GEOM_minLON) RANGE [-60,-30]
      NUM_TEST $(GEOM_minLAT) RANGE [70,90]
      NUM_TEST $(GEOM_maxLON) RANGE [-60,-30]",<pass>
    <pass> -> FeatureReader_44 [INITIATOR]
FeatureReader_44
    ATTRIBUTES = TIFF,
    ATTR_ACCUM_MODE = Only Use Result
    COMBINE_GEOM = Use Result
    COORDSYS = LL-WGS84
    DATASET = $(FME_MF_DIR_ENCODED)DEM\N70\70n060w_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
N70W30: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [70,90]
      NUM_TEST $(GEOM_maxLON) RANGE [-30,0]
      NUM_TEST $(GEOM_maxLAT) RANGE [70,90]
      NUM_TEST $(GEOM_minLON) RANGE [-30,0]
      NUM_TEST $(GEOM_minLAT) RANGE [70,90]
      NUM_TEST $(GEOM_minLON) RANGE [-30,0]
      NUM_TEST $(GEOM_minLAT) RANGE [70,90]
      NUM_TEST $(GEOM_maxLON) RANGE [-30,0]",<pass>
    <pass> -> FeatureReader_39 [INITIATOR]
FeatureReader_39
    ATTRIBUTES = TIFF,
    ATTR_ACCUM_MODE = Only Use Result
    COMBINE_GEOM = Use Result
    COORDSYS = LL-WGS84
    DATASET = $(FME_MF_DIR_ENCODED)DEM\N70\70n030w_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
N50E0: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [50,70]
      NUM_TEST $(GEOM_maxLON) RANGE [0,30]
      NUM_TEST $(GEOM_maxLAT) RANGE [50,70]
      NUM_TEST $(GEOM_minLON) RANGE [0,30]
      NUM_TEST $(GEOM_minLAT) RANGE [50,70]
      NUM_TEST $(GEOM_minLON) RANGE [0,30]
      NUM_TEST $(GEOM_minLAT) RANGE [50,70]
      NUM_TEST $(GEOM_maxLON) RANGE [0,30]",<pass>
    <pass> -> FeatureReader_26 [INITIATOR]
FeatureReader_26
    ATTRIBUTES = TIFF,
    ATTR_ACCUM_MODE = Only Use Result
    COMBINE_GEOM = Use Result
    COORDSYS = LL-WGS84
    DATASET = $(FME_MF_DIR_ENCODED)DEM\N50\50n000e_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
N50E30: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [50,70]
      NUM_TEST $(GEOM_maxLON) RANGE [30,60]
      NUM_TEST $(GEOM_maxLAT) RANGE [50,70]
      NUM_TEST $(GEOM_minLON) RANGE [30,60]
      NUM_TEST $(GEOM_minLAT) RANGE [50,70]
      NUM_TEST $(GEOM_minLON) RANGE [30,60]
      NUM_TEST $(GEOM_minLAT) RANGE [50,70]
      NUM_TEST $(GEOM_maxLON) RANGE [30,60]",<pass>
    <pass> -> FeatureReader_25 [INITIATOR]
FeatureReader_25
    ATTRIBUTES = TIFF,
    ATTR_ACCUM_MODE = Only Use Result
    COMBINE_GEOM = Use Result
    DATASET = $(FME_MF_DIR_ENCODED)DEM\N50\50n030e_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
N50E60: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [50,70]
      NUM_TEST $(GEOM_maxLON) RANGE [60,90]
      NUM_TEST $(GEOM_maxLAT) RANGE [50,70]
      NUM_TEST $(GEOM_minLON) RANGE [60,90]
      NUM_TEST $(GEOM_minLAT) RANGE [50,70]
      NUM_TEST $(GEOM_minLON) RANGE [60,90]
      NUM_TEST $(GEOM_minLAT) RANGE [50,70]
      NUM_TEST $(GEOM_maxLON) RANGE [60,90]",<pass>
    <pass> -> FeatureReader_28 [INITIATOR]
FeatureReader_28
    ATTRIBUTES = TIFF,
    ATTR_ACCUM_MODE = Only Use Result
    COMBINE_GEOM = Use Result
    COORDSYS = LL-WGS84
    DATASET = $(FME_MF_DIR_ENCODED)DEM\N50\50n060e_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
N50E90: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [50,70]
      NUM_TEST $(GEOM_maxLON) RANGE [90,120]
      NUM_TEST $(GEOM_maxLAT) RANGE [50,70]
      NUM_TEST $(GEOM_minLON) RANGE [90,120]
      NUM_TEST $(GEOM_minLAT) RANGE [50,70]
      NUM_TEST $(GEOM_minLON) RANGE [90,120]
      NUM_TEST $(GEOM_minLAT) RANGE [50,70]
      NUM_TEST $(GEOM_maxLON) RANGE [90,120]",<pass>
    <pass> -> FeatureReader_29 [INITIATOR]
FeatureReader_29
    ATTRIBUTES = TIFF,
    ATTR_ACCUM_MODE = Only Use Result
    COMBINE_GEOM = Use Result
    COORDSYS = LL-WGS84
    DATASET = $(FME_MF_DIR_ENCODED)DEM\N50\50n090e_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
N50E120: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [50,70]
      NUM_TEST $(GEOM_maxLON) RANGE [120,150]
      NUM_TEST $(GEOM_maxLAT) RANGE [50,70]
      NUM_TEST $(GEOM_minLON) RANGE [120,150]
      NUM_TEST $(GEOM_minLAT) RANGE [50,70]
      NUM_TEST $(GEOM_minLON) RANGE [120,150]
      NUM_TEST $(GEOM_minLAT) RANGE [50,70]
      NUM_TEST $(GEOM_maxLON) RANGE [120,150]",<pass>
    <pass> -> FeatureReader_30 [INITIATOR]
FeatureReader_30
    ATTRIBUTES = TIFF,
    ATTR_ACCUM_MODE = Only Use Result
    COMBINE_GEOM = Use Result
    COORDSYS = LL-WGS84
    DATASET = $(FME_MF_DIR_ENCODED)DEM\N50\50n120e_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
N50E150: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [50,70]
      NUM_TEST $(GEOM_maxLON) RANGE [150,180]
      NUM_TEST $(GEOM_maxLAT) RANGE [50,70]
      NUM_TEST $(GEOM_minLON) RANGE [150,180]
      NUM_TEST $(GEOM_minLAT) RANGE [50,70]
      NUM_TEST $(GEOM_minLON) RANGE [150,180]
      NUM_TEST $(GEOM_minLAT) RANGE [50,70]
      NUM_TEST $(GEOM_maxLON) RANGE [150,180]",<pass>
    <pass> -> FeatureReader_31 [INITIATOR]
FeatureReader_31
    ATTRIBUTES = TIFF,
    ATTR_ACCUM_MODE = Only Use Result
    COMBINE_GEOM = Use Result
    COORDSYS = LL-WGS84
    DATASET = $(FME_MF_DIR_ENCODED)DEM\N50\50n150e_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
N50W180: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [50,70]
      NUM_TEST $(GEOM_maxLON) RANGE [-180,-150]
      NUM_TEST $(GEOM_maxLAT) RANGE [50,70]
      NUM_TEST $(GEOM_minLON) RANGE [-180,-150]
      NUM_TEST $(GEOM_minLAT) RANGE [50,70]
      NUM_TEST $(GEOM_minLON) RANGE [-180,-150]
      NUM_TEST $(GEOM_minLAT) RANGE [50,70]
      NUM_TEST $(GEOM_maxLON) RANGE [-180,-150]",<pass>
    <pass> -> FeatureReader_36 [INITIATOR]
FeatureReader_36
    ATTRIBUTES = TIFF,
    ATTR_ACCUM_MODE = Only Use Result
    COMBINE_GEOM = Use Result
    COORDSYS = LL-WGS84
    DATASET = $(FME_MF_DIR_ENCODED)DEM\N50\50n180w_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
N50W150: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [50,70]
      NUM_TEST $(GEOM_maxLON) RANGE [-150,-120]
      NUM_TEST $(GEOM_maxLAT) RANGE [50,70]
      NUM_TEST $(GEOM_minLON) RANGE [-150,-120]
      NUM_TEST $(GEOM_minLAT) RANGE [50,70]
      NUM_TEST $(GEOM_minLON) RANGE [-150,-120]
      NUM_TEST $(GEOM_minLAT) RANGE [50,70]
      NUM_TEST $(GEOM_maxLON) RANGE [-150,-120]",<pass>
    <pass> -> FeatureReader_35 [INITIATOR]
FeatureReader_35
    ATTRIBUTES = TIFF,
    ATTR_ACCUM_MODE = Only Use Result
    COMBINE_GEOM = Use Result
    COORDSYS = LL-WGS84
    DATASET = $(FME_MF_DIR_ENCODED)DEM\N50\50n150w_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
N50W120: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [50,70]
      NUM_TEST $(GEOM_maxLON) RANGE [-120,-90]
      NUM_TEST $(GEOM_maxLAT) RANGE [50,70]
      NUM_TEST $(GEOM_minLON) RANGE [-120,-90]
      NUM_TEST $(GEOM_minLAT) RANGE [50,70]
      NUM_TEST $(GEOM_minLON) RANGE [-120,-90]
      NUM_TEST $(GEOM_minLAT) RANGE [50,70]
      NUM_TEST $(GEOM_maxLON) RANGE [-120,-90]",<pass>
    <pass> -> FeatureReader_34 [INITIATOR]
FeatureReader_34
    ATTRIBUTES = TIFF,
    ATTR_ACCUM_MODE = Only Use Result
    COMBINE_GEOM = Use Result
    COORDSYS = LL-WGS84
    DATASET = $(FME_MF_DIR_ENCODED)DEM\N50\50n120w_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
N50W90: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [50,70]
      NUM_TEST $(GEOM_maxLON) RANGE [-90,-60]
      NUM_TEST $(GEOM_maxLAT) RANGE [50,70]
      NUM_TEST $(GEOM_minLON) RANGE [-90,-60]
      NUM_TEST $(GEOM_minLAT) RANGE [50,70]
      NUM_TEST $(GEOM_minLON) RANGE [-90,-60]
      NUM_TEST $(GEOM_minLAT) RANGE [50,70]
      NUM_TEST $(GEOM_maxLON) RANGE [-90,-60]",<pass>
    <pass> -> FeatureReader_33 [INITIATOR]
FeatureReader_33
    ATTRIBUTES = TIFF,
    ATTR_ACCUM_MODE = Only Use Result
    COMBINE_GEOM = Use Result
    COORDSYS = LL-WGS84
    DATASET = $(FME_MF_DIR_ENCODED)DEM\N50\50n090w_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
N50W60: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [50,70]
      NUM_TEST $(GEOM_maxLON) RANGE [-60,-30]
      NUM_TEST $(GEOM_maxLAT) RANGE [50,70]
      NUM_TEST $(GEOM_minLON) RANGE [-60,-30]
      NUM_TEST $(GEOM_minLAT) RANGE [50,70]
      NUM_TEST $(GEOM_minLON) RANGE [-60,-30]
      NUM_TEST $(GEOM_minLAT) RANGE [50,70]
      NUM_TEST $(GEOM_maxLON) RANGE [-60,-30]",<pass>
    <pass> -> FeatureReader_32 [INITIATOR]
FeatureReader_32
    ATTRIBUTES = TIFF,
    ATTR_ACCUM_MODE = Only Use Result
    COMBINE_GEOM = Use Result
    COORDSYS = LL-WGS84
    DATASET = $(FME_MF_DIR_ENCODED)DEM\N50\50n060w_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
N50W30: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [50,70]
      NUM_TEST $(GEOM_maxLON) RANGE [-30,0]
      NUM_TEST $(GEOM_maxLAT) RANGE [50,70]
      NUM_TEST $(GEOM_minLON) RANGE [-30,0]
      NUM_TEST $(GEOM_minLAT) RANGE [50,70]
      NUM_TEST $(GEOM_minLON) RANGE [-30,0]
      NUM_TEST $(GEOM_minLAT) RANGE [50,70]
      NUM_TEST $(GEOM_maxLON) RANGE [-30,0]",<pass>
    <pass> -> FeatureReader_27 [INITIATOR]
FeatureReader_27
    ATTRIBUTES = TIFF,
    ATTR_ACCUM_MODE = Only Use Result
    COMBINE_GEOM = Use Result
    COORDSYS = LL-WGS84
    DATASET = $(FME_MF_DIR_ENCODED)DEM\N50\50n030w_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
N30E0: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [30,50]
      NUM_TEST $(GEOM_maxLON) RANGE [0,30]
      NUM_TEST $(GEOM_maxLAT) RANGE [30,50]
      NUM_TEST $(GEOM_minLON) RANGE [0,30]
      NUM_TEST $(GEOM_minLAT) RANGE [30,50]
      NUM_TEST $(GEOM_minLON) RANGE [0,30]
      NUM_TEST $(GEOM_minLAT) RANGE [30,50]
      NUM_TEST $(GEOM_maxLON) RANGE [0,30]",<pass>
    <pass> -> FeatureReader_14 [INITIATOR]
FeatureReader_14
    ATTRIBUTES = TIFF,
    ATTR_ACCUM_MODE = Only Use Result
    COMBINE_GEOM = Use Result
    COORDSYS = LL-WGS84
    DATASET = $(FME_MF_DIR_ENCODED)DEM\N30\30n000e_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
N30E30: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [30,50]
      NUM_TEST $(GEOM_maxLON) RANGE [30,60]
      NUM_TEST $(GEOM_maxLAT) RANGE [30,50]
      NUM_TEST $(GEOM_minLON) RANGE [30,60]
      NUM_TEST $(GEOM_minLAT) RANGE [30,50]
      NUM_TEST $(GEOM_minLON) RANGE [30,60]
      NUM_TEST $(GEOM_minLAT) RANGE [30,50]
      NUM_TEST $(GEOM_maxLON) RANGE [30,60]",<pass>
    <pass> -> FeatureReader_13 [INITIATOR]
FeatureReader_13
    ATTRIBUTES = TIFF,
    ATTR_ACCUM_MODE = Only Use Result
    COMBINE_GEOM = Use Result
    DATASET = $(FME_MF_DIR_ENCODED)DEM\N30\30n030e_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
N30E60: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [30,50]
      NUM_TEST $(GEOM_maxLON) RANGE [60,90]
      NUM_TEST $(GEOM_maxLAT) RANGE [30,50]
      NUM_TEST $(GEOM_minLON) RANGE [60,90]
      NUM_TEST $(GEOM_minLAT) RANGE [30,50]
      NUM_TEST $(GEOM_minLON) RANGE [60,90]
      NUM_TEST $(GEOM_minLAT) RANGE [30,50]
      NUM_TEST $(GEOM_maxLON) RANGE [60,90]",<pass>
    <pass> -> FeatureReader_16 [INITIATOR]
FeatureReader_16
    ATTRIBUTES = TIFF,
    ATTR_ACCUM_MODE = Only Use Result
    COMBINE_GEOM = Use Result
    COORDSYS = LL-WGS84
    DATASET = $(FME_MF_DIR_ENCODED)DEM\N30\30n060e_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
N30E90: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [30,50]
      NUM_TEST $(GEOM_maxLON) RANGE [90,120]
      NUM_TEST $(GEOM_maxLAT) RANGE [30,50]
      NUM_TEST $(GEOM_minLON) RANGE [90,120]
      NUM_TEST $(GEOM_minLAT) RANGE [30,50]
      NUM_TEST $(GEOM_minLON) RANGE [90,120]
      NUM_TEST $(GEOM_minLAT) RANGE [30,50]
      NUM_TEST $(GEOM_maxLON) RANGE [90,120]",<pass>
    <pass> -> FeatureReader_17 [INITIATOR]
FeatureReader_17
    ATTRIBUTES = TIFF,
    ATTR_ACCUM_MODE = Only Use Result
    COMBINE_GEOM = Use Result
    COORDSYS = LL-WGS84
    DATASET = $(FME_MF_DIR_ENCODED)DEM\N30\30n090e_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
N30E120: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [30,50]
      NUM_TEST $(GEOM_maxLON) RANGE [120,150]
      NUM_TEST $(GEOM_maxLAT) RANGE [30,50]
      NUM_TEST $(GEOM_minLON) RANGE [120,150]
      NUM_TEST $(GEOM_minLAT) RANGE [30,50]
      NUM_TEST $(GEOM_minLON) RANGE [120,150]
      NUM_TEST $(GEOM_minLAT) RANGE [30,50]
      NUM_TEST $(GEOM_maxLON) RANGE [120,150]",<pass>
    <pass> -> FeatureReader_18 [INITIATOR]
FeatureReader_18
    ATTRIBUTES = TIFF,
    ATTR_ACCUM_MODE = Only Use Result
    COMBINE_GEOM = Use Result
    COORDSYS = LL-WGS84
    DATASET = $(FME_MF_DIR_ENCODED)DEM\N30\30n120e_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
N30E150: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [30,50]
      NUM_TEST $(GEOM_maxLON) RANGE [150,180]
      NUM_TEST $(GEOM_maxLAT) RANGE [30,50]
      NUM_TEST $(GEOM_minLON) RANGE [150,180]
      NUM_TEST $(GEOM_minLAT) RANGE [30,50]
      NUM_TEST $(GEOM_minLON) RANGE [150,180]
      NUM_TEST $(GEOM_minLAT) RANGE [30,50]
      NUM_TEST $(GEOM_maxLON) RANGE [150,180]",<pass>
    <pass> -> FeatureReader_19 [INITIATOR]
FeatureReader_19
    ATTRIBUTES = TIFF,
    ATTR_ACCUM_MODE = Only Use Result
    COMBINE_GEOM = Use Result
    COORDSYS = LL-WGS84
    DATASET = $(FME_MF_DIR_ENCODED)DEM\N30\30n150e_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
N30W180: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [30,50]
      NUM_TEST $(GEOM_maxLON) RANGE [-180,-150]
      NUM_TEST $(GEOM_maxLAT) RANGE [30,50]
      NUM_TEST $(GEOM_minLON) RANGE [-180,-150]
      NUM_TEST $(GEOM_minLAT) RANGE [30,50]
      NUM_TEST $(GEOM_minLON) RANGE [-180,-150]
      NUM_TEST $(GEOM_minLAT) RANGE [30,60]
      NUM_TEST $(GEOM_maxLON) RANGE [-180,-150]",<pass>
    <pass> -> FeatureReader_24 [INITIATOR]
FeatureReader_24
    ATTRIBUTES = TIFF,
    ATTR_ACCUM_MODE = Only Use Result
    COMBINE_GEOM = Use Result
    COORDSYS = LL-WGS84
    DATASET = $(FME_MF_DIR_ENCODED)DEM\N30\30n180w_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
N30W150: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [30,50]
      NUM_TEST $(GEOM_maxLON) RANGE [-150,-120]
      NUM_TEST $(GEOM_maxLAT) RANGE [30,50]
      NUM_TEST $(GEOM_minLON) RANGE [-150,-120]
      NUM_TEST $(GEOM_minLAT) RANGE [30,50]
      NUM_TEST $(GEOM_minLON) RANGE [-150,-120]
      NUM_TEST $(GEOM_minLAT) RANGE [30,50]
      NUM_TEST $(GEOM_maxLON) RANGE [-150,-120]",<pass>
    <pass> -> FeatureReader_23 [INITIATOR]
FeatureReader_23
    ATTRIBUTES = TIFF,
    ATTR_ACCUM_MODE = Only Use Result
    COMBINE_GEOM = Use Result
    COORDSYS = LL-WGS84
    DATASET = $(FME_MF_DIR_ENCODED)DEM\N30\30n150w_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
N30W120: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [30,50]
      NUM_TEST $(GEOM_maxLON) RANGE [-120,-90]
      NUM_TEST $(GEOM_maxLAT) RANGE [30,50]
      NUM_TEST $(GEOM_minLON) RANGE [-120,-90]
      NUM_TEST $(GEOM_minLAT) RANGE [30,50]
      NUM_TEST $(GEOM_minLON) RANGE [-120,-90]
      NUM_TEST $(GEOM_minLAT) RANGE [30,50]
      NUM_TEST $(GEOM_maxLON) RANGE [-120,-90]",<pass>
    <pass> -> FeatureReader_22 [INITIATOR]
FeatureReader_22
    ATTRIBUTES = TIFF,
    ATTR_ACCUM_MODE = Only Use Result
    COMBINE_GEOM = Use Result
    COORDSYS = LL-WGS84
    DATASET = $(FME_MF_DIR_ENCODED)DEM\N30\30n120w_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
N30W90: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [30,50]
      NUM_TEST $(GEOM_maxLON) RANGE [-90,-60]
      NUM_TEST $(GEOM_maxLAT) RANGE [30,50]
      NUM_TEST $(GEOM_minLON) RANGE [-90,-60]
      NUM_TEST $(GEOM_minLAT) RANGE [30,50]
      NUM_TEST $(GEOM_minLON) RANGE [-90,-60]
      NUM_TEST $(GEOM_minLAT) RANGE [30,50]
      NUM_TEST $(GEOM_maxLON) RANGE [-90,-60]",<pass>
    <pass> -> FeatureReader_21 [INITIATOR]
FeatureReader_21
    ATTRIBUTES = TIFF,
    ATTR_ACCUM_MODE = Only Use Result
    COMBINE_GEOM = Use Result
    COORDSYS = LL-WGS84
    DATASET = $(FME_MF_DIR_ENCODED)DEM\N30\30n090w_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
N30W60: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [30,50]
      NUM_TEST $(GEOM_maxLON) RANGE [-60,-30]
      NUM_TEST $(GEOM_maxLAT) RANGE [30,50]
      NUM_TEST $(GEOM_minLON) RANGE [-60,-30]
      NUM_TEST $(GEOM_minLAT) RANGE [30,50]
      NUM_TEST $(GEOM_minLON) RANGE [-60,-30]
      NUM_TEST $(GEOM_minLAT) RANGE [30,50]
      NUM_TEST $(GEOM_maxLON) RANGE [-60,-30]",<pass>
    <pass> -> FeatureReader_20 [INITIATOR]
FeatureReader_20
    ATTRIBUTES = TIFF,
    ATTR_ACCUM_MODE = Only Use Result
    COMBINE_GEOM = Use Result
    COORDSYS = LL-WGS84
    DATASET = $(FME_MF_DIR_ENCODED)DEM\N30\30n060w_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
N30W30: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [30,50]
      NUM_TEST $(GEOM_maxLON) RANGE [-30,0]
      NUM_TEST $(GEOM_maxLAT) RANGE [30,50]
      NUM_TEST $(GEOM_minLON) RANGE [-30,0]
      NUM_TEST $(GEOM_minLAT) RANGE [30,50]
      NUM_TEST $(GEOM_minLON) RANGE [-30,0]
      NUM_TEST $(GEOM_minLAT) RANGE [30,50]
      NUM_TEST $(GEOM_maxLON) RANGE [-30,0]",<pass>
    <pass> -> FeatureReader_15 [INITIATOR]
FeatureReader_15
    ATTRIBUTES = TIFF,
    ATTR_ACCUM_MODE = Only Use Result
    COMBINE_GEOM = Use Result
    COORDSYS = LL-WGS84
    DATASET = $(FME_MF_DIR_ENCODED)DEM\N30\30n030w_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
N10E0: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [10,30]
      NUM_TEST $(GEOM_maxLON) RANGE [0,30]
      NUM_TEST $(GEOM_maxLAT) RANGE [10,30]
      NUM_TEST $(GEOM_minLON) RANGE [0,30]
      NUM_TEST $(GEOM_minLAT) RANGE [10,30]
      NUM_TEST $(GEOM_minLON) RANGE [0,30]
      NUM_TEST $(GEOM_minLAT) RANGE [10,30]
      NUM_TEST $(GEOM_maxLON) RANGE [0,30]",<pass>
    <pass> -> FeatureReader_2 [INITIATOR]
FeatureReader_2
    ATTRIBUTES = TIFF,
    ATTR_ACCUM_MODE = Only Use Result
    COMBINE_GEOM = Use Result
    COORDSYS = LL-WGS84
    DATASET = $(FME_MF_DIR_ENCODED)DEM\N10\10n000e_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
N10E30: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [10,30]
      NUM_TEST $(GEOM_maxLON) RANGE [30,60]
      NUM_TEST $(GEOM_maxLAT) RANGE [10,30]
      NUM_TEST $(GEOM_minLON) RANGE [30,60]
      NUM_TEST $(GEOM_minLAT) RANGE [10,30]
      NUM_TEST $(GEOM_minLON) RANGE [30,60]
      NUM_TEST $(GEOM_minLAT) RANGE [10,30]
      NUM_TEST $(GEOM_maxLON) RANGE [30,60]",<pass>
    <pass> -> FeatureReader [INITIATOR]
FeatureReader
    ATTRIBUTES = TIFF,
    ATTR_ACCUM_MODE = Only Use Result
    COMBINE_GEOM = Use Result
    DATASET = $(FME_MF_DIR_ENCODED)DEM\N10\10n030e_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
N10E60: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [10,30]
      NUM_TEST $(GEOM_maxLON) RANGE [60,90]
      NUM_TEST $(GEOM_maxLAT) RANGE [10,30]
      NUM_TEST $(GEOM_minLON) RANGE [60,90]
      NUM_TEST $(GEOM_minLAT) RANGE [10,30]
      NUM_TEST $(GEOM_minLON) RANGE [60,90]
      NUM_TEST $(GEOM_minLAT) RANGE [10,30]
      NUM_TEST $(GEOM_maxLON) RANGE [60,90]",<pass>
    <pass> -> FeatureReader_4 [INITIATOR]
FeatureReader_4
    ATTRIBUTES = TIFF,
    ATTR_ACCUM_MODE = Only Use Result
    COMBINE_GEOM = Use Result
    COORDSYS = LL-WGS84
    DATASET = $(FME_MF_DIR_ENCODED)DEM\N10\10n060e_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
N10E90: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [10,30]
      NUM_TEST $(GEOM_maxLON) RANGE [90,120]
      NUM_TEST $(GEOM_maxLAT) RANGE [10,30]
      NUM_TEST $(GEOM_minLON) RANGE [90,120]
      NUM_TEST $(GEOM_minLAT) RANGE [10,30]
      NUM_TEST $(GEOM_minLON) RANGE [90,120]
      NUM_TEST $(GEOM_minLAT) RANGE [10,30]
      NUM_TEST $(GEOM_maxLON) RANGE [90,120]",<pass>
    <pass> -> FeatureReader_5 [INITIATOR]
FeatureReader_5
    ATTRIBUTES = TIFF,
    ATTR_ACCUM_MODE = Only Use Result
    COMBINE_GEOM = Use Result
    COORDSYS = LL-WGS84
    DATASET = $(FME_MF_DIR_ENCODED)DEM\N10\10n090e_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
N10E120: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [10,30]
      NUM_TEST $(GEOM_maxLON) RANGE [120,150]
      NUM_TEST $(GEOM_maxLAT) RANGE [10,30]
      NUM_TEST $(GEOM_minLON) RANGE [120,150]
      NUM_TEST $(GEOM_minLAT) RANGE [10,30]
      NUM_TEST $(GEOM_minLON) RANGE [120,150]
      NUM_TEST $(GEOM_minLAT) RANGE [10,30]
      NUM_TEST $(GEOM_maxLON) RANGE [120,150]",<pass>
    <pass> -> FeatureReader_6 [INITIATOR]
FeatureReader_6
    ATTRIBUTES = TIFF,
    ATTR_ACCUM_MODE = Only Use Result
    COMBINE_GEOM = Use Result
    COORDSYS = LL-WGS84
    DATASET = $(FME_MF_DIR_ENCODED)DEM\N10\10n120e_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
N10E150: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [10,30]
      NUM_TEST $(GEOM_maxLON) RANGE [150,180]
      NUM_TEST $(GEOM_maxLAT) RANGE [10,30]
      NUM_TEST $(GEOM_minLON) RANGE [150,180]
      NUM_TEST $(GEOM_minLAT) RANGE [10,30]
      NUM_TEST $(GEOM_minLON) RANGE [150,180]
      NUM_TEST $(GEOM_minLAT) RANGE [10,30]
      NUM_TEST $(GEOM_maxLON) RANGE [150,180]",<pass>
    <pass> -> FeatureReader_7 [INITIATOR]
FeatureReader_7
    ATTRIBUTES = TIFF,
    ATTR_ACCUM_MODE = Only Use Result
    COMBINE_GEOM = Use Result
    COORDSYS = LL-WGS84
    DATASET = $(FME_MF_DIR_ENCODED)DEM\N10\10n150e_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
N10W180: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [10,30]
      NUM_TEST $(GEOM_maxLON) RANGE [-180,-150]
      NUM_TEST $(GEOM_maxLAT) RANGE [10,30]
      NUM_TEST $(GEOM_minLON) RANGE [-180,-150]
      NUM_TEST $(GEOM_minLAT) RANGE [10,30]
      NUM_TEST $(GEOM_minLON) RANGE [-180,-150]
      NUM_TEST $(GEOM_minLAT) RANGE [10,30]
      NUM_TEST $(GEOM_maxLON) RANGE [-180,-150]",<pass>
    <pass> -> FeatureReader_12 [INITIATOR]
FeatureReader_12
    ATTRIBUTES = TIFF,
    ATTR_ACCUM_MODE = Only Use Result
    COMBINE_GEOM = Use Result
    COORDSYS = LL-WGS84
    DATASET = $(FME_MF_DIR_ENCODED)DEM\N10\10n180w_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
N10W150: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [10,30]
      NUM_TEST $(GEOM_maxLON) RANGE [-150,-120]
      NUM_TEST $(GEOM_maxLAT) RANGE [10,30]
      NUM_TEST $(GEOM_minLON) RANGE [-150,-120]
      NUM_TEST $(GEOM_minLAT) RANGE [10,30]
      NUM_TEST $(GEOM_minLON) RANGE [-150,-120]
      NUM_TEST $(GEOM_minLAT) RANGE [10,30]
      NUM_TEST $(GEOM_maxLON) RANGE [-150,-120]",<pass>
    <pass> -> FeatureReader_11 [INITIATOR]
FeatureReader_11
    ATTRIBUTES = TIFF,
    ATTR_ACCUM_MODE = Only Use Result
    COMBINE_GEOM = Use Result
    COORDSYS = LL-WGS84
    DATASET = $(FME_MF_DIR_ENCODED)DEM\N10\10n150w_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
N10W120: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [10,30]
      NUM_TEST $(GEOM_maxLON) RANGE [-120,-90]
      NUM_TEST $(GEOM_maxLAT) RANGE [10,30]
      NUM_TEST $(GEOM_minLON) RANGE [-120,-90]
      NUM_TEST $(GEOM_minLAT) RANGE [10,30]
      NUM_TEST $(GEOM_minLON) RANGE [-120,-90]
      NUM_TEST $(GEOM_minLAT) RANGE [10,30]
      NUM_TEST $(GEOM_maxLON) RANGE [-120,-90]",<pass>
    <pass> -> FeatureReader_10 [INITIATOR]
FeatureReader_10
    ATTRIBUTES = TIFF,
    ATTR_ACCUM_MODE = Only Use Result
    COMBINE_GEOM = Use Result
    COORDSYS = LL-WGS84
    DATASET = $(FME_MF_DIR_ENCODED)DEM\N10\10n120w_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
N10W90: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [10,30]
      NUM_TEST $(GEOM_maxLON) RANGE [-90,-60]
      NUM_TEST $(GEOM_maxLAT) RANGE [10,30]
      NUM_TEST $(GEOM_minLON) RANGE [-90,-60]
      NUM_TEST $(GEOM_minLAT) RANGE [10,30]
      NUM_TEST $(GEOM_minLON) RANGE [-90,-60]
      NUM_TEST $(GEOM_minLAT) RANGE [10,30]
      NUM_TEST $(GEOM_maxLON) RANGE [-90,-60]",<pass>
    <pass> -> FeatureReader_9 [INITIATOR]
FeatureReader_9
    ATTRIBUTES = TIFF,
    ATTR_ACCUM_MODE = Only Use Result
    COMBINE_GEOM = Use Result
    COORDSYS = LL-WGS84
    DATASET = $(FME_MF_DIR_ENCODED)DEM\N10\10n090w_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
N10W60: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [10,30]
      NUM_TEST $(GEOM_maxLON) RANGE [-60,-30]
      NUM_TEST $(GEOM_maxLAT) RANGE [10,30]
      NUM_TEST $(GEOM_minLON) RANGE [-60,-30]
      NUM_TEST $(GEOM_minLAT) RANGE [10,30]
      NUM_TEST $(GEOM_minLON) RANGE [-60,-30]
      NUM_TEST $(GEOM_minLAT) RANGE [10,30]
      NUM_TEST $(GEOM_maxLON) RANGE [-60,-30]",<pass>
    <pass> -> FeatureReader_8 [INITIATOR]
FeatureReader_8
    ATTRIBUTES = TIFF,
    ATTR_ACCUM_MODE = Only Use Result
    COMBINE_GEOM = Use Result
    COORDSYS = LL-WGS84
    DATASET = $(FME_MF_DIR_ENCODED)DEM\N10\10n060w_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
N10W30: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [10,30]
      NUM_TEST $(GEOM_maxLON) RANGE [-30,0]
      NUM_TEST $(GEOM_maxLAT) RANGE [10,30]
      NUM_TEST $(GEOM_minLON) RANGE [-30,0]
      NUM_TEST $(GEOM_minLAT) RANGE [10,30]
      NUM_TEST $(GEOM_minLON) RANGE [-30,0]
      NUM_TEST $(GEOM_minLAT) RANGE [10,30]
      NUM_TEST $(GEOM_maxLON) RANGE [-30,0]",<pass>
    <pass> -> FeatureReader_3 [INITIATOR]
FeatureReader_3
    ATTRIBUTES = TIFF,
    ATTR_ACCUM_MODE = Only Use Result
    COMBINE_GEOM = Use Result
    COORDSYS = LL-WGS84
    DATASET = $(FME_MF_DIR_ENCODED)DEM\N10\10n030w_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S10E0: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-10,10]
      NUM_TEST $(GEOM_maxLON) RANGE [0,30]
      NUM_TEST $(GEOM_maxLAT) RANGE [-10,10]
      NUM_TEST $(GEOM_minLON) RANGE [0,30]
      NUM_TEST $(GEOM_minLAT) RANGE [-10,10]
      NUM_TEST $(GEOM_minLON) RANGE [0,30]
      NUM_TEST $(GEOM_minLAT) RANGE [-10,10]
      NUM_TEST $(GEOM_maxLON) RANGE [0,30]",<pass>
    <pass> -> FeatureReader_50 [INITIATOR]
FeatureReader_50
    ATTRIBUTES = TIFF,
    ATTR_ACCUM_MODE = Only Use Result
    COMBINE_GEOM = Use Result
    COORDSYS = LL-WGS84
    DATASET = $(FME_MF_DIR_ENCODED)DEM\S10\10s000e_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S10E30: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-10,10]
      NUM_TEST $(GEOM_maxLON) RANGE [30,60]
      NUM_TEST $(GEOM_maxLAT) RANGE [-10,10]
      NUM_TEST $(GEOM_minLON) RANGE [30,60]
      NUM_TEST $(GEOM_minLAT) RANGE [-10,10]
      NUM_TEST $(GEOM_minLON) RANGE [30,60]
      NUM_TEST $(GEOM_minLAT) RANGE [-10,10]
      NUM_TEST $(GEOM_maxLON) RANGE [30,60]",<pass>
    <pass> -> FeatureReader_49 [INITIATOR]
FeatureReader_49
    ATTRIBUTES = TIFF,
    ATTR_ACCUM_MODE = Only Use Result
    COMBINE_GEOM = Use Result
    COORDSYS = LL-WGS84
    DATASET = $(FME_MF_DIR_ENCODED)DEM\S10\10s030e_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S10E60: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-10,10]
      NUM_TEST $(GEOM_maxLON) RANGE [60,90]
      NUM_TEST $(GEOM_maxLAT) RANGE [-10,10]
      NUM_TEST $(GEOM_minLON) RANGE [60,90]
      NUM_TEST $(GEOM_minLAT) RANGE [-10,10]
      NUM_TEST $(GEOM_minLON) RANGE [60,90]
      NUM_TEST $(GEOM_minLAT) RANGE [-10,10]
      NUM_TEST $(GEOM_maxLON) RANGE [60,90]",<pass>
    <pass> -> FeatureReader_52 [INITIATOR]
FeatureReader_52
    ATTRIBUTES = TIFF,
    ATTR_ACCUM_MODE = Only Use Result
    COMBINE_GEOM = Use Result
    COORDSYS = LL-WGS84
    DATASET = $(FME_MF_DIR_ENCODED)DEM\S10\10s060e_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S10E90: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-10,10]
      NUM_TEST $(GEOM_maxLON) RANGE [90,120]
      NUM_TEST $(GEOM_maxLAT) RANGE [-10,10]
      NUM_TEST $(GEOM_minLON) RANGE [90,120]
      NUM_TEST $(GEOM_minLAT) RANGE [-10,10]
      NUM_TEST $(GEOM_minLON) RANGE [90,120]
      NUM_TEST $(GEOM_minLAT) RANGE [-10,10]
      NUM_TEST $(GEOM_maxLON) RANGE [90,120]",<pass>
    <pass> -> FeatureReader_53 [INITIATOR]
FeatureReader_53
    ATTRIBUTES = TIFF,
    ATTR_ACCUM_MODE = Only Use Result
    COMBINE_GEOM = Use Result
    COORDSYS = LL-WGS84
    DATASET = $(FME_MF_DIR_ENCODED)DEM\S10\10s090e_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S10E120: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-10,10]
      NUM_TEST $(GEOM_maxLON) RANGE [120,150]
      NUM_TEST $(GEOM_maxLAT) RANGE [-10,10]
      NUM_TEST $(GEOM_minLON) RANGE [120,150]
      NUM_TEST $(GEOM_minLAT) RANGE [-10,10]
      NUM_TEST $(GEOM_minLON) RANGE [120,150]
      NUM_TEST $(GEOM_minLAT) RANGE [-10,10]
      NUM_TEST $(GEOM_maxLON) RANGE [120,150]",<pass>
    <pass> -> FeatureReader_54 [INITIATOR]
FeatureReader_54
    ATTRIBUTES = TIFF,
    ATTR_ACCUM_MODE = Only Use Result
    COMBINE_GEOM = Use Result
    COORDSYS = LL-WGS84
    DATASET = $(FME_MF_DIR_ENCODED)DEM\S10\10s120e_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S10E150: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-10,10]
      NUM_TEST $(GEOM_maxLON) RANGE [150,180]
      NUM_TEST $(GEOM_maxLAT) RANGE [-10,10]
      NUM_TEST $(GEOM_minLON) RANGE [150,180]
      NUM_TEST $(GEOM_minLAT) RANGE [-10,10]
      NUM_TEST $(GEOM_minLON) RANGE [150,180]
      NUM_TEST $(GEOM_minLAT) RANGE [-10,10]
      NUM_TEST $(GEOM_maxLON) RANGE [150,180]",<pass>
    <pass> -> FeatureReader_55 [INITIATOR]
FeatureReader_55
    ATTRIBUTES = TIFF,
    ATTR_ACCUM_MODE = Only Use Result
    COMBINE_GEOM = Use Result
    COORDSYS = LL-WGS84
    DATASET = $(FME_MF_DIR_ENCODED)DEM\S10\10s150e_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S10W30: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-10,10]
      NUM_TEST $(GEOM_maxLON) RANGE [-30,0]
      NUM_TEST $(GEOM_maxLAT) RANGE [-10,10]
      NUM_TEST $(GEOM_minLON) RANGE [-30,0]
      NUM_TEST $(GEOM_minLAT) RANGE [-10,10]
      NUM_TEST $(GEOM_minLON) RANGE [-30,0]
      NUM_TEST $(GEOM_minLAT) RANGE [-10,10]
      NUM_TEST $(GEOM_maxLON) RANGE [-30,0]",<pass>
    <pass> -> FeatureReader_51 [INITIATOR]
FeatureReader_51
    ATTRIBUTES = TIFF,
    ATTR_ACCUM_MODE = Only Use Result
    COMBINE_GEOM = Use Result
    COORDSYS = LL-WGS84
    DATASET = $(FME_MF_DIR_ENCODED)DEM\S10\10s030w_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S10W60: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-10,10]
      NUM_TEST $(GEOM_maxLON) RANGE [-60,-30]
      NUM_TEST $(GEOM_maxLAT) RANGE [-10,10]
      NUM_TEST $(GEOM_minLON) RANGE [-60,-30]
      NUM_TEST $(GEOM_minLAT) RANGE [-10,10]
      NUM_TEST $(GEOM_minLON) RANGE [-60,-30]
      NUM_TEST $(GEOM_minLAT) RANGE [-10,10]
      NUM_TEST $(GEOM_maxLON) RANGE [-60,-30]",<pass>
    <pass> -> FeatureReader_56 [INITIATOR]
FeatureReader_56
    ATTRIBUTES = TIFF,
    ATTR_ACCUM_MODE = Only Use Result
    COMBINE_GEOM = Use Result
    COORDSYS = LL-WGS84
    DATASET = $(FME_MF_DIR_ENCODED)DEM\S10\10s060w_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S10W90: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-10,10]
      NUM_TEST $(GEOM_maxLON) RANGE [-90,-60]
      NUM_TEST $(GEOM_maxLAT) RANGE [-10,10]
      NUM_TEST $(GEOM_minLON) RANGE [-90,-60]
      NUM_TEST $(GEOM_minLAT) RANGE [-10,10]
      NUM_TEST $(GEOM_minLON) RANGE [-90,-60]
      NUM_TEST $(GEOM_minLAT) RANGE [-10,10]
      NUM_TEST $(GEOM_maxLON) RANGE [-90,-60]",<pass>
    <pass> -> FeatureReader_57 [INITIATOR]
FeatureReader_57
    ATTRIBUTES = TIFF,
    ATTR_ACCUM_MODE = Only Use Result
    COMBINE_GEOM = Use Result
    COORDSYS = LL-WGS84
    DATASET = $(FME_MF_DIR_ENCODED)DEM\S10\10s090w_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S10W120: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-10,10]
      NUM_TEST $(GEOM_maxLON) RANGE [-120,-90]
      NUM_TEST $(GEOM_maxLAT) RANGE [-10,10]
      NUM_TEST $(GEOM_minLON) RANGE [-120,-90]
      NUM_TEST $(GEOM_minLAT) RANGE [-10,10]
      NUM_TEST $(GEOM_minLON) RANGE [-120,-90]
      NUM_TEST $(GEOM_minLAT) RANGE [-10,10]
      NUM_TEST $(GEOM_maxLON) RANGE [-120,-90]",<pass>
    <pass> -> FeatureReader_58 [INITIATOR]
FeatureReader_58
    ATTRIBUTES = TIFF,
    ATTR_ACCUM_MODE = Only Use Result
    COMBINE_GEOM = Use Result
    COORDSYS = LL-WGS84
    DATASET = $(FME_MF_DIR_ENCODED)DEM\S10\10s120w_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S10W150: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-10,10]
      NUM_TEST $(GEOM_maxLON) RANGE [-150,-120]
      NUM_TEST $(GEOM_maxLAT) RANGE [-10,10]
      NUM_TEST $(GEOM_minLON) RANGE [-150,-120]
      NUM_TEST $(GEOM_minLAT) RANGE [-10,10]
      NUM_TEST $(GEOM_minLON) RANGE [-150,-120]
      NUM_TEST $(GEOM_minLAT) RANGE [-10,10]
      NUM_TEST $(GEOM_maxLON) RANGE [-150,-120]",<pass>
    <pass> -> FeatureReader_59 [INITIATOR]
FeatureReader_59
    ATTRIBUTES = TIFF,
    ATTR_ACCUM_MODE = Only Use Result
    COMBINE_GEOM = Use Result
    COORDSYS = LL-WGS84
    DATASET = $(FME_MF_DIR_ENCODED)DEM\S10\10s150w_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S10W180: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-10,10]
      NUM_TEST $(GEOM_maxLON) RANGE [-180,-150]
      NUM_TEST $(GEOM_maxLAT) RANGE [-10,10]
      NUM_TEST $(GEOM_minLON) RANGE [-180,-150]
      NUM_TEST $(GEOM_minLAT) RANGE [-10,10]
      NUM_TEST $(GEOM_minLON) RANGE [-180,-150]
      NUM_TEST $(GEOM_minLAT) RANGE [-10,10]
      NUM_TEST $(GEOM_maxLON) RANGE [-180,-150]",<pass>
    <pass> -> FeatureReader_60 [INITIATOR]
FeatureReader_60
    ATTRIBUTES = TIFF,
    ATTR_ACCUM_MODE = Only Use Result
    COMBINE_GEOM = Use Result
    COORDSYS = LL-WGS84
    DATASET = $(FME_MF_DIR_ENCODED)DEM\S10\10s180w_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S30E0: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-30,-10]
      NUM_TEST $(GEOM_maxLON) RANGE [0,30]
      NUM_TEST $(GEOM_maxLAT) RANGE [-30,-10]
      NUM_TEST $(GEOM_minLON) RANGE [0,30]
      NUM_TEST $(GEOM_minLAT) RANGE [-30,-10]
      NUM_TEST $(GEOM_minLON) RANGE [0,30]
      NUM_TEST $(GEOM_minLAT) RANGE [-30,-10]
      NUM_TEST $(GEOM_maxLON) RANGE [0,30]",<pass>
    <pass> -> FeatureReader_62 [INITIATOR]
FeatureReader_62
    ATTRIBUTES = TIFF,
    ATTR_ACCUM_MODE = Only Use Result
    COMBINE_GEOM = Use Result
    COORDSYS = LL-WGS84
    DATASET = $(FME_MF_DIR_ENCODED)DEM\S30\30s000e_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S30E30: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-30,-10]
      NUM_TEST $(GEOM_maxLON) RANGE [30,60]
      NUM_TEST $(GEOM_maxLAT) RANGE [-30,-10]
      NUM_TEST $(GEOM_minLON) RANGE [30,60]
      NUM_TEST $(GEOM_minLAT) RANGE [-30,-10]
      NUM_TEST $(GEOM_minLON) RANGE [30,60]
      NUM_TEST $(GEOM_minLAT) RANGE [-30,-10]
      NUM_TEST $(GEOM_maxLON) RANGE [30,60]",<pass>
    <pass> -> FeatureReader_61 [INITIATOR]
FeatureReader_61
    ATTRIBUTES = TIFF,
    ATTR_ACCUM_MODE = Only Use Result
    COMBINE_GEOM = Use Result
    COORDSYS = LL-WGS84
    DATASET = $(FME_MF_DIR_ENCODED)DEM\S30\30s030e_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S30E60: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-30,-10]
      NUM_TEST $(GEOM_maxLON) RANGE [60,90]
      NUM_TEST $(GEOM_maxLAT) RANGE [-30,-10]
      NUM_TEST $(GEOM_minLON) RANGE [60,90]
      NUM_TEST $(GEOM_minLAT) RANGE [-30,-10]
      NUM_TEST $(GEOM_minLON) RANGE [60,90]
      NUM_TEST $(GEOM_minLAT) RANGE [-30,-10]
      NUM_TEST $(GEOM_maxLON) RANGE [60,90]",<pass>
    <pass> -> FeatureReader_64 [INITIATOR]
FeatureReader_64
    ATTRIBUTES = TIFF,
    ATTR_ACCUM_MODE = Only Use Result
    COMBINE_GEOM = Use Result
    COORDSYS = LL-WGS84
    DATASET = $(FME_MF_DIR_ENCODED)DEM\S30\30s060e_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S30E90: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-30,-10]
      NUM_TEST $(GEOM_maxLON) RANGE [90,120]
      NUM_TEST $(GEOM_maxLAT) RANGE [-30,-10]
      NUM_TEST $(GEOM_minLON) RANGE [90,120]
      NUM_TEST $(GEOM_minLAT) RANGE [-30,-10]
      NUM_TEST $(GEOM_minLON) RANGE [90,120]
      NUM_TEST $(GEOM_minLAT) RANGE [-30,-10]
      NUM_TEST $(GEOM_maxLON) RANGE [90,120]",<pass>
    <pass> -> FeatureReader_65 [INITIATOR]
FeatureReader_65
    ATTRIBUTES = TIFF,
    ATTR_ACCUM_MODE = Only Use Result
    COMBINE_GEOM = Use Result
    COORDSYS = LL-WGS84
    DATASET = $(FME_MF_DIR_ENCODED)DEM\S30\30s090e_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S30E120: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-30,-10]
      NUM_TEST $(GEOM_maxLON) RANGE [120,150]
      NUM_TEST $(GEOM_maxLAT) RANGE [-30,-10]
      NUM_TEST $(GEOM_minLON) RANGE [120,150]
      NUM_TEST $(GEOM_minLAT) RANGE [-30,-10]
      NUM_TEST $(GEOM_minLON) RANGE [120,150]
      NUM_TEST $(GEOM_minLAT) RANGE [-30,-10]
      NUM_TEST $(GEOM_maxLON) RANGE [120,150]",<pass>
    <pass> -> FeatureReader_66 [INITIATOR]
FeatureReader_66
    ATTRIBUTES = TIFF,
    ATTR_ACCUM_MODE = Only Use Result
    COMBINE_GEOM = Use Result
    COORDSYS = LL-WGS84
    DATASET = $(FME_MF_DIR_ENCODED)DEM\S30\30s120e_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S30E150: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-30,-10]
      NUM_TEST $(GEOM_maxLON) RANGE [150,180]
      NUM_TEST $(GEOM_maxLAT) RANGE [-30,-10]
      NUM_TEST $(GEOM_minLON) RANGE [150,180]
      NUM_TEST $(GEOM_minLAT) RANGE [-30,-10]
      NUM_TEST $(GEOM_minLON) RANGE [150,180]
      NUM_TEST $(GEOM_minLAT) RANGE [-30,-10]
      NUM_TEST $(GEOM_maxLON) RANGE [150,180]",<pass>
    <pass> -> FeatureReader_67 [INITIATOR]
FeatureReader_67
    ATTRIBUTES = TIFF,
    ATTR_ACCUM_MODE = Only Use Result
    COMBINE_GEOM = Use Result
    COORDSYS = LL-WGS84
    DATASET = $(FME_MF_DIR_ENCODED)DEM\S30\30s150e_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S30W30: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-30,-10]
      NUM_TEST $(GEOM_maxLON) RANGE [-30,0]
      NUM_TEST $(GEOM_maxLAT) RANGE [-30,-10]
      NUM_TEST $(GEOM_minLON) RANGE [-30,0]
      NUM_TEST $(GEOM_minLAT) RANGE [-30,-10]
      NUM_TEST $(GEOM_minLON) RANGE [-30,0]
      NUM_TEST $(GEOM_minLAT) RANGE [-30,-10]
      NUM_TEST $(GEOM_maxLON) RANGE [-30,0]",<pass>
    <pass> -> FeatureReader_63 [INITIATOR]
FeatureReader_63
    ATTRIBUTES = TIFF,
    ATTR_ACCUM_MODE = Only Use Result
    COMBINE_GEOM = Use Result
    COORDSYS = LL-WGS84
    DATASET = $(FME_MF_DIR_ENCODED)DEM\S30\30s030w_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S30W60: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-30,-10]
      NUM_TEST $(GEOM_maxLON) RANGE [-60,-30]
      NUM_TEST $(GEOM_maxLAT) RANGE [-30,-10]
      NUM_TEST $(GEOM_minLON) RANGE [-60,-30]
      NUM_TEST $(GEOM_minLAT) RANGE [-30,-10]
      NUM_TEST $(GEOM_minLON) RANGE [-60,-30]
      NUM_TEST $(GEOM_minLAT) RANGE [-30,-10]
      NUM_TEST $(GEOM_maxLON) RANGE [-60,-30]",<pass>
    <pass> -> FeatureReader_68 [INITIATOR]
FeatureReader_68
    ATTRIBUTES = TIFF,
    ATTR_ACCUM_MODE = Only Use Result
    COMBINE_GEOM = Use Result
    COORDSYS = LL-WGS84
    DATASET = $(FME_MF_DIR_ENCODED)DEM\S30\30s060w_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S30W90: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-30,-10]
      NUM_TEST $(GEOM_maxLON) RANGE [-90,-60]
      NUM_TEST $(GEOM_maxLAT) RANGE [-30,-10]
      NUM_TEST $(GEOM_minLON) RANGE [-90,-60]
      NUM_TEST $(GEOM_minLAT) RANGE [-30,-10]
      NUM_TEST $(GEOM_minLON) RANGE [-90,-60]
      NUM_TEST $(GEOM_minLAT) RANGE [-30,-10]
      NUM_TEST $(GEOM_maxLON) RANGE [-90,-60]",<pass>
    <pass> -> FeatureReader_69 [INITIATOR]
FeatureReader_69
    ATTRIBUTES = TIFF,
    ATTR_ACCUM_MODE = Only Use Result
    COMBINE_GEOM = Use Result
    COORDSYS = LL-WGS84
    DATASET = $(FME_MF_DIR_ENCODED)DEM\S30\30s090w_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S30W120: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-30,-10]
      NUM_TEST $(GEOM_maxLON) RANGE [-120,-90]
      NUM_TEST $(GEOM_maxLAT) RANGE [-30,-10]
      NUM_TEST $(GEOM_minLON) RANGE [-120,-90]
      NUM_TEST $(GEOM_minLAT) RANGE [-30,-10]
      NUM_TEST $(GEOM_minLON) RANGE [-120,-90]
      NUM_TEST $(GEOM_minLAT) RANGE [-30,-10]
      NUM_TEST $(GEOM_maxLON) RANGE [-120,-90]",<pass>
    <pass> -> FeatureReader_70 [INITIATOR]
FeatureReader_70
    ATTRIBUTES = TIFF,
    ATTR_ACCUM_MODE = Only Use Result
    COMBINE_GEOM = Use Result
    COORDSYS = LL-WGS84
    DATASET = $(FME_MF_DIR_ENCODED)DEM\S30\30s120w_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S30W150: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-30,-10]
      NUM_TEST $(GEOM_maxLON) RANGE [-150,-120]
      NUM_TEST $(GEOM_maxLAT) RANGE [-30,-10]
      NUM_TEST $(GEOM_minLON) RANGE [-150,-120]
      NUM_TEST $(GEOM_minLAT) RANGE [-30,-10]
      NUM_TEST $(GEOM_minLON) RANGE [-150,-120]
      NUM_TEST $(GEOM_minLAT) RANGE [-30,-10]
      NUM_TEST $(GEOM_maxLON) RANGE [-150,-120]",<pass>
    <pass> -> FeatureReader_71 [INITIATOR]
FeatureReader_71
    ATTRIBUTES = TIFF,
    ATTR_ACCUM_MODE = Only Use Result
    COMBINE_GEOM = Use Result
    COORDSYS = LL-WGS84
    DATASET = $(FME_MF_DIR_ENCODED)DEM\S30\30s150w_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S30W180: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-30,-10]
      NUM_TEST $(GEOM_maxLON) RANGE [-180,-150]
      NUM_TEST $(GEOM_maxLAT) RANGE [-30,-10]
      NUM_TEST $(GEOM_minLON) RANGE [-180,-150]
      NUM_TEST $(GEOM_minLAT) RANGE [-30,-10]
      NUM_TEST $(GEOM_minLON) RANGE [-180,-150]
      NUM_TEST $(GEOM_minLAT) RANGE [-30,-10]
      NUM_TEST $(GEOM_maxLON) RANGE [-180,-150]",<pass>
    <pass> -> FeatureReader_72 [INITIATOR]
FeatureReader_72
    ATTRIBUTES = TIFF,
    ATTR_ACCUM_MODE = Only Use Result
    COMBINE_GEOM = Use Result
    COORDSYS = LL-WGS84
    DATASET = $(FME_MF_DIR_ENCODED)DEM\S30\30s180w_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S50E0: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-50,-30]
      NUM_TEST $(GEOM_maxLON) RANGE [0,30]
      NUM_TEST $(GEOM_maxLAT) RANGE [-50,-30]
      NUM_TEST $(GEOM_minLON) RANGE [0,30]
      NUM_TEST $(GEOM_minLAT) RANGE [-50,-30]
      NUM_TEST $(GEOM_minLON) RANGE [0,30]
      NUM_TEST $(GEOM_minLAT) RANGE [-50,-30]
      NUM_TEST $(GEOM_maxLON) RANGE [0,30]",<pass>
    <pass> -> FeatureReader_74 [INITIATOR]
FeatureReader_74
    ATTRIBUTES = TIFF,
    ATTR_ACCUM_MODE = Only Use Result
    COMBINE_GEOM = Use Result
    COORDSYS = LL-WGS84
    DATASET = $(FME_MF_DIR_ENCODED)DEM\S50\50s000e_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S50E30: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-50,-30]
      NUM_TEST $(GEOM_maxLON) RANGE [30,60]
      NUM_TEST $(GEOM_maxLAT) RANGE [-50,-30]
      NUM_TEST $(GEOM_minLON) RANGE [30,60]
      NUM_TEST $(GEOM_minLAT) RANGE [-50,-30]
      NUM_TEST $(GEOM_minLON) RANGE [30,60]
      NUM_TEST $(GEOM_minLAT) RANGE [-50,-30]
      NUM_TEST $(GEOM_maxLON) RANGE [30,60]",<pass>
    <pass> -> FeatureReader_73 [INITIATOR]
FeatureReader_73
    ATTRIBUTES = TIFF,
    ATTR_ACCUM_MODE = Only Use Result
    COMBINE_GEOM = Use Result
    COORDSYS = LL-WGS84
    DATASET = $(FME_MF_DIR_ENCODED)DEM\S50\50s030e_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S50E60: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-50,-30]
      NUM_TEST $(GEOM_maxLON) RANGE [60,90]
      NUM_TEST $(GEOM_maxLAT) RANGE [-50,-30]
      NUM_TEST $(GEOM_minLON) RANGE [60,90]
      NUM_TEST $(GEOM_minLAT) RANGE [-50,-30]
      NUM_TEST $(GEOM_minLON) RANGE [60,90]
      NUM_TEST $(GEOM_minLAT) RANGE [-50,-30]
      NUM_TEST $(GEOM_maxLON) RANGE [60,90]",<pass>
    <pass> -> FeatureReader_76 [INITIATOR]
FeatureReader_76
    ATTRIBUTES = TIFF,
    ATTR_ACCUM_MODE = Only Use Result
    COMBINE_GEOM = Use Result
    COORDSYS = LL-WGS84
    DATASET = $(FME_MF_DIR_ENCODED)DEM\S50\50s060e_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S50E90: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-50,-30]
      NUM_TEST $(GEOM_maxLON) RANGE [90,120]
      NUM_TEST $(GEOM_maxLAT) RANGE [-50,-30]
      NUM_TEST $(GEOM_minLON) RANGE [90,120]
      NUM_TEST $(GEOM_minLAT) RANGE [-50,-30]
      NUM_TEST $(GEOM_minLON) RANGE [90,120]
      NUM_TEST $(GEOM_minLAT) RANGE [-50,-30]
      NUM_TEST $(GEOM_maxLON) RANGE [90,120]",<pass>
    <pass> -> FeatureReader_77 [INITIATOR]
FeatureReader_77
    ATTRIBUTES = TIFF,
    ATTR_ACCUM_MODE = Only Use Result
    COMBINE_GEOM = Use Result
    COORDSYS = LL-WGS84
    DATASET = $(FME_MF_DIR_ENCODED)DEM\S50\50s090e_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S50E120: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-50,-30]
      NUM_TEST $(GEOM_maxLON) RANGE [120,150]
      NUM_TEST $(GEOM_maxLAT) RANGE [-50,-30]
      NUM_TEST $(GEOM_minLON) RANGE [120,150]
      NUM_TEST $(GEOM_minLAT) RANGE [-50,-30]
      NUM_TEST $(GEOM_minLON) RANGE [120,150]
      NUM_TEST $(GEOM_minLAT) RANGE [-50,-30]
      NUM_TEST $(GEOM_maxLON) RANGE [120,150]",<pass>
    <pass> -> FeatureReader_78 [INITIATOR]
FeatureReader_78
    ATTRIBUTES = TIFF,
    ATTR_ACCUM_MODE = Only Use Result
    COMBINE_GEOM = Use Result
    COORDSYS = LL-WGS84
    DATASET = $(FME_MF_DIR_ENCODED)DEM\S50\50s120e_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S50E150: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-50,-30]
      NUM_TEST $(GEOM_maxLON) RANGE [150,180]
      NUM_TEST $(GEOM_maxLAT) RANGE [-50,-30]
      NUM_TEST $(GEOM_minLON) RANGE [150,180]
      NUM_TEST $(GEOM_minLAT) RANGE [-50,-30]
      NUM_TEST $(GEOM_minLON) RANGE [150,180]
      NUM_TEST $(GEOM_minLAT) RANGE [-50,-30]
      NUM_TEST $(GEOM_maxLON) RANGE [150,180]",<pass>
    <pass> -> FeatureReader_79 [INITIATOR]
FeatureReader_79
    ATTRIBUTES = TIFF,
    ATTR_ACCUM_MODE = Only Use Result
    COMBINE_GEOM = Use Result
    COORDSYS = LL-WGS84
    DATASET = $(FME_MF_DIR_ENCODED)DEM\S50\50s150e_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S50W30: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-50,-30]
      NUM_TEST $(GEOM_maxLON) RANGE [-30,0]
      NUM_TEST $(GEOM_maxLAT) RANGE [-50,-30]
      NUM_TEST $(GEOM_minLON) RANGE [-30,0]
      NUM_TEST $(GEOM_minLAT) RANGE [-50,-30]
      NUM_TEST $(GEOM_minLON) RANGE [-30,0]
      NUM_TEST $(GEOM_minLAT) RANGE [-50,-30]
      NUM_TEST $(GEOM_maxLON) RANGE [-30,0]",<pass>
    <pass> -> FeatureReader_75 [INITIATOR]
FeatureReader_75
    ATTRIBUTES = TIFF,
    ATTR_ACCUM_MODE = Only Use Result
    COMBINE_GEOM = Use Result
    COORDSYS = LL-WGS84
    DATASET = $(FME_MF_DIR_ENCODED)DEM\S50\50s030w_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S50W60: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-50,-30]
      NUM_TEST $(GEOM_maxLON) RANGE [-60,-30]
      NUM_TEST $(GEOM_maxLAT) RANGE [-50,-30]
      NUM_TEST $(GEOM_minLON) RANGE [-60,-30]
      NUM_TEST $(GEOM_minLAT) RANGE [-50,-30]
      NUM_TEST $(GEOM_minLON) RANGE [-60,-30]
      NUM_TEST $(GEOM_minLAT) RANGE [-50,-30]
      NUM_TEST $(GEOM_maxLON) RANGE [-60,-30]",<pass>
    <pass> -> FeatureReader_80 [INITIATOR]
FeatureReader_80
    ATTRIBUTES = TIFF,
    ATTR_ACCUM_MODE = Only Use Result
    COMBINE_GEOM = Use Result
    COORDSYS = LL-WGS84
    DATASET = $(FME_MF_DIR_ENCODED)DEM\S50\50s060w_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S50W90: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-50,-30]
      NUM_TEST $(GEOM_maxLON) RANGE [-90,-60]
      NUM_TEST $(GEOM_maxLAT) RANGE [-50,-30]
      NUM_TEST $(GEOM_minLON) RANGE [-90,-60]
      NUM_TEST $(GEOM_minLAT) RANGE [-50,-30]
      NUM_TEST $(GEOM_minLON) RANGE [-90,-60]
      NUM_TEST $(GEOM_minLAT) RANGE [-50,-30]
      NUM_TEST $(GEOM_maxLON) RANGE [-90,-60]",<pass>
    <pass> -> FeatureReader_81 [INITIATOR]
FeatureReader_81
    ATTRIBUTES = TIFF,
    ATTR_ACCUM_MODE = Only Use Result
    COMBINE_GEOM = Use Result
    COORDSYS = LL-WGS84
    DATASET = $(FME_MF_DIR_ENCODED)DEM\S50\50s090w_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S50W120: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-50,-30]
      NUM_TEST $(GEOM_maxLON) RANGE [-120,-90]
      NUM_TEST $(GEOM_maxLAT) RANGE [-50,-30]
      NUM_TEST $(GEOM_minLON) RANGE [-120,-90]
      NUM_TEST $(GEOM_minLAT) RANGE [-50,-30]
      NUM_TEST $(GEOM_minLON) RANGE [-120,-90]
      NUM_TEST $(GEOM_minLAT) RANGE [-50,-30]
      NUM_TEST $(GEOM_maxLON) RANGE [-120,-90]",<pass>
    <pass> -> FeatureReader_82 [INITIATOR]
FeatureReader_82
    ATTRIBUTES = TIFF,
    ATTR_ACCUM_MODE = Only Use Result
    COMBINE_GEOM = Use Result
    COORDSYS = LL-WGS84
    DATASET = $(FME_MF_DIR_ENCODED)DEM\S50\50s120w_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S50W150: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-50,-30]
      NUM_TEST $(GEOM_maxLON) RANGE [-150,-120]
      NUM_TEST $(GEOM_maxLAT) RANGE [-50,-30]
      NUM_TEST $(GEOM_minLON) RANGE [-150,-120]
      NUM_TEST $(GEOM_minLAT) RANGE [-50,-30]
      NUM_TEST $(GEOM_minLON) RANGE [-150,-120]
      NUM_TEST $(GEOM_minLAT) RANGE [-50,-30]
      NUM_TEST $(GEOM_maxLON) RANGE [-150,-120]",<pass>
    <pass> -> FeatureReader_83 [INITIATOR]
FeatureReader_83
    ATTRIBUTES = TIFF,
    ATTR_ACCUM_MODE = Only Use Result
    COMBINE_GEOM = Use Result
    COORDSYS = LL-WGS84
    DATASET = $(FME_MF_DIR_ENCODED)DEM\S50\50s150w_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S50W180: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-50,-30]
      NUM_TEST $(GEOM_maxLON) RANGE [-180,-150]
      NUM_TEST $(GEOM_maxLAT) RANGE [-50,-30]
      NUM_TEST $(GEOM_minLON) RANGE [-180,-150]
      NUM_TEST $(GEOM_minLAT) RANGE [-50,-30]
      NUM_TEST $(GEOM_minLON) RANGE [-180,-150]
      NUM_TEST $(GEOM_minLAT) RANGE [-50,-30]
      NUM_TEST $(GEOM_maxLON) RANGE [-180,-150]",<pass>
    <pass> -> FeatureReader_84 [INITIATOR]
FeatureReader_84
    ATTRIBUTES = TIFF,
    ATTR_ACCUM_MODE = Only Use Result
    COMBINE_GEOM = Use Result
    COORDSYS = LL-WGS84
    DATASET = $(FME_MF_DIR_ENCODED)DEM\S50\50s180w_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S70E0: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-70,-50]
      NUM_TEST $(GEOM_maxLON) RANGE [0,30]
      NUM_TEST $(GEOM_maxLAT) RANGE [-70,-50]
      NUM_TEST $(GEOM_minLON) RANGE [0,30]
      NUM_TEST $(GEOM_minLAT) RANGE [-70,-50]
      NUM_TEST $(GEOM_minLON) RANGE [0,30]
      NUM_TEST $(GEOM_minLAT) RANGE [-70,-50]
      NUM_TEST $(GEOM_maxLON) RANGE [0,30]",<pass>
    <pass> -> FeatureReader_86 [INITIATOR]
FeatureReader_86
    ATTRIBUTES = TIFF,
    ATTR_ACCUM_MODE = Only Use Result
    COMBINE_GEOM = Use Result
    COORDSYS = LL-WGS84
    DATASET = $(FME_MF_DIR_ENCODED)DEM\S70\70s000e_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S70E30: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-70,-50]
      NUM_TEST $(GEOM_maxLON) RANGE [30,60]
      NUM_TEST $(GEOM_maxLAT) RANGE [-70,-50]
      NUM_TEST $(GEOM_minLON) RANGE [30,60]
      NUM_TEST $(GEOM_minLAT) RANGE [-70,-50]
      NUM_TEST $(GEOM_minLON) RANGE [30,60]
      NUM_TEST $(GEOM_minLAT) RANGE [-70,-50]
      NUM_TEST $(GEOM_maxLON) RANGE [30,60]",<pass>
    <pass> -> FeatureReader_85 [INITIATOR]
FeatureReader_85
    ATTRIBUTES = TIFF,
    ATTR_ACCUM_MODE = Only Use Result
    COMBINE_GEOM = Use Result
    COORDSYS = LL-WGS84
    DATASET = $(FME_MF_DIR_ENCODED)DEM\S70\70s030e_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S70E60: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-70,-50]
      NUM_TEST $(GEOM_maxLON) RANGE [60,90]
      NUM_TEST $(GEOM_maxLAT) RANGE [-70,-50]
      NUM_TEST $(GEOM_minLON) RANGE [60,90]
      NUM_TEST $(GEOM_minLAT) RANGE [-70,-50]
      NUM_TEST $(GEOM_minLON) RANGE [60,90]
      NUM_TEST $(GEOM_minLAT) RANGE [-70,-50]
      NUM_TEST $(GEOM_maxLON) RANGE [60,90]",<pass>
    <pass> -> FeatureReader_88 [INITIATOR]
FeatureReader_88
    ATTRIBUTES = TIFF,
    ATTR_ACCUM_MODE = Only Use Result
    COMBINE_GEOM = Use Result
    COORDSYS = LL-WGS84
    DATASET = $(FME_MF_DIR_ENCODED)DEM\S70\70s060e_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S70E90: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-70,-50]
      NUM_TEST $(GEOM_maxLON) RANGE [90,120]
      NUM_TEST $(GEOM_maxLAT) RANGE [-70,-50]
      NUM_TEST $(GEOM_minLON) RANGE [90,120]
      NUM_TEST $(GEOM_minLAT) RANGE [-70,-50]
      NUM_TEST $(GEOM_minLON) RANGE [90,120]
      NUM_TEST $(GEOM_minLAT) RANGE [-70,-50]
      NUM_TEST $(GEOM_maxLON) RANGE [90,120]",<pass>
    <pass> -> FeatureReader_89 [INITIATOR]
FeatureReader_89
    ATTRIBUTES = TIFF,
    ATTR_ACCUM_MODE = Only Use Result
    COMBINE_GEOM = Use Result
    COORDSYS = LL-WGS84
    DATASET = $(FME_MF_DIR_ENCODED)DEM\S70\70s090e_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S70E120: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-70,-50]
      NUM_TEST $(GEOM_maxLON) RANGE [120,150]
      NUM_TEST $(GEOM_maxLAT) RANGE [-70,-50]
      NUM_TEST $(GEOM_minLON) RANGE [120,150]
      NUM_TEST $(GEOM_minLAT) RANGE [-70,-50]
      NUM_TEST $(GEOM_minLON) RANGE [120,150]
      NUM_TEST $(GEOM_minLAT) RANGE [-70,-50]
      NUM_TEST $(GEOM_maxLON) RANGE [120,150]",<pass>
    <pass> -> FeatureReader_90 [INITIATOR]
FeatureReader_90
    ATTRIBUTES = TIFF,
    ATTR_ACCUM_MODE = Only Use Result
    COMBINE_GEOM = Use Result
    COORDSYS = LL-WGS84
    DATASET = $(FME_MF_DIR_ENCODED)DEM\S70\70s120e_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S70E150: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-70,-50]
      NUM_TEST $(GEOM_maxLON) RANGE [150,180]
      NUM_TEST $(GEOM_maxLAT) RANGE [-70,-50]
      NUM_TEST $(GEOM_minLON) RANGE [150,180]
      NUM_TEST $(GEOM_minLAT) RANGE [-70,-50]
      NUM_TEST $(GEOM_minLON) RANGE [150,180]
      NUM_TEST $(GEOM_minLAT) RANGE [-70,-50]
      NUM_TEST $(GEOM_maxLON) RANGE [150,180]",<pass>
    <pass> -> FeatureReader_91 [INITIATOR]
FeatureReader_91
    ATTRIBUTES = TIFF,
    ATTR_ACCUM_MODE = Only Use Result
    COMBINE_GEOM = Use Result
    COORDSYS = LL-WGS84
    DATASET = $(FME_MF_DIR_ENCODED)DEM\S70\70s150e_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S70W30: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-70,-50]
      NUM_TEST $(GEOM_maxLON) RANGE [-30,0]
      NUM_TEST $(GEOM_maxLAT) RANGE [-70,-50]
      NUM_TEST $(GEOM_minLON) RANGE [-30,0]
      NUM_TEST $(GEOM_minLAT) RANGE [-70,-50]
      NUM_TEST $(GEOM_minLON) RANGE [-30,0]
      NUM_TEST $(GEOM_minLAT) RANGE [-70,-50]
      NUM_TEST $(GEOM_maxLON) RANGE [-30,0]",<pass>
    <pass> -> FeatureReader_87 [INITIATOR]
FeatureReader_87
    ATTRIBUTES = TIFF,
    ATTR_ACCUM_MODE = Only Use Result
    COMBINE_GEOM = Use Result
    COORDSYS = LL-WGS84
    DATASET = $(FME_MF_DIR_ENCODED)DEM\S70\70s030w_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S70W60: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-70,-50]
      NUM_TEST $(GEOM_maxLON) RANGE [-60,-30]
      NUM_TEST $(GEOM_maxLAT) RANGE [-70,-50]
      NUM_TEST $(GEOM_minLON) RANGE [-60,-30]
      NUM_TEST $(GEOM_minLAT) RANGE [-70,-50]
      NUM_TEST $(GEOM_minLON) RANGE [-60,-30]
      NUM_TEST $(GEOM_minLAT) RANGE [-70,-50]
      NUM_TEST $(GEOM_maxLON) RANGE [-60,-30]",<pass>
    <pass> -> FeatureReader_92 [INITIATOR]
FeatureReader_92
    ATTRIBUTES = TIFF,
    ATTR_ACCUM_MODE = Only Use Result
    COMBINE_GEOM = Use Result
    COORDSYS = LL-WGS84
    DATASET = $(FME_MF_DIR_ENCODED)DEM\S70\70s060w_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S70W90: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-70,-50]
      NUM_TEST $(GEOM_maxLON) RANGE [-90,-60]
      NUM_TEST $(GEOM_maxLAT) RANGE [-70,-50]
      NUM_TEST $(GEOM_minLON) RANGE [-90,-60]
      NUM_TEST $(GEOM_minLAT) RANGE [-70,-50]
      NUM_TEST $(GEOM_minLON) RANGE [-90,-60]
      NUM_TEST $(GEOM_minLAT) RANGE [-70,-50]
      NUM_TEST $(GEOM_maxLON) RANGE [-90,-60]",<pass>
    <pass> -> FeatureReader_93 [INITIATOR]
FeatureReader_93
    ATTRIBUTES = TIFF,
    ATTR_ACCUM_MODE = Only Use Result
    COMBINE_GEOM = Use Result
    COORDSYS = LL-WGS84
    DATASET = $(FME_MF_DIR_ENCODED)DEM\S70\70s090w_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S70W120: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-70,-50]
      NUM_TEST $(GEOM_maxLON) RANGE [-120,-90]
      NUM_TEST $(GEOM_maxLAT) RANGE [-70,-50]
      NUM_TEST $(GEOM_minLON) RANGE [-120,-90]
      NUM_TEST $(GEOM_minLAT) RANGE [-70,-50]
      NUM_TEST $(GEOM_minLON) RANGE [-120,-90]
      NUM_TEST $(GEOM_minLAT) RANGE [-70,-50]
      NUM_TEST $(GEOM_maxLON) RANGE [-120,-90]",<pass>
    <pass> -> FeatureReader_94 [INITIATOR]
FeatureReader_94
    ATTRIBUTES = TIFF,
    ATTR_ACCUM_MODE = Only Use Result
    COMBINE_GEOM = Use Result
    COORDSYS = LL-WGS84
    DATASET = $(FME_MF_DIR_ENCODED)DEM\S70\70s120w_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S70W150: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-70,-50]
      NUM_TEST $(GEOM_maxLON) RANGE [-150,-120]
      NUM_TEST $(GEOM_maxLAT) RANGE [-70,-50]
      NUM_TEST $(GEOM_minLON) RANGE [-150,-120]
      NUM_TEST $(GEOM_minLAT) RANGE [-70,-50]
      NUM_TEST $(GEOM_minLON) RANGE [-150,-120]
      NUM_TEST $(GEOM_minLAT) RANGE [-70,-50]
      NUM_TEST $(GEOM_maxLON) RANGE [-150,-120]",<pass>
    <pass> -> FeatureReader_95 [INITIATOR]
FeatureReader_95
    ATTRIBUTES = TIFF,
    ATTR_ACCUM_MODE = Only Use Result
    COMBINE_GEOM = Use Result
    COORDSYS = LL-WGS84
    DATASET = $(FME_MF_DIR_ENCODED)DEM\S70\70s150w_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S70W180: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-70,-50]
      NUM_TEST $(GEOM_maxLON) RANGE [-180,-150]
      NUM_TEST $(GEOM_maxLAT) RANGE [-70,-50]
      NUM_TEST $(GEOM_minLON) RANGE [-180,-150]
      NUM_TEST $(GEOM_minLAT) RANGE [-70,-50]
      NUM_TEST $(GEOM_minLON) RANGE [-180,-150]
      NUM_TEST $(GEOM_minLAT) RANGE [-70,-50]
      NUM_TEST $(GEOM_maxLON) RANGE [-180,-150]",<pass>
    <pass> -> FeatureReader_96 [INITIATOR]
FeatureReader_96
    ATTRIBUTES = TIFF,
    ATTR_ACCUM_MODE = Only Use Result
    COMBINE_GEOM = Use Result
    COORDSYS = LL-WGS84
    DATASET = $(FME_MF_DIR_ENCODED)DEM\S70\70s180w_20101117_gmted_dsc075.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S90E0: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-90,-70]
      NUM_TEST $(GEOM_maxLON) RANGE [0,30]
      NUM_TEST $(GEOM_maxLAT) RANGE [-90,-70]
      NUM_TEST $(GEOM_minLON) RANGE [0,30]
      NUM_TEST $(GEOM_minLAT) RANGE [-90,-70]
      NUM_TEST $(GEOM_minLON) RANGE [0,30]
      NUM_TEST $(GEOM_minLAT) RANGE [-90,-70]
      NUM_TEST $(GEOM_maxLON) RANGE [0,30]",<pass>
    <pass> -> FeatureReader_98 [INITIATOR]
FeatureReader_98
    ATTRIBUTES = TIFF,
    ATTR_ACCUM_MODE = Only Use Result
    COMBINE_GEOM = Use Result
    COORDSYS = LL-WGS84
    DATASET = $(FME_MF_DIR_ENCODED)DEM\S90\90s000e_20101117_gmted_dsc300.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S90E30: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-90,-70]
      NUM_TEST $(GEOM_maxLON) RANGE [30,60]
      NUM_TEST $(GEOM_maxLAT) RANGE [-90,-70]
      NUM_TEST $(GEOM_minLON) RANGE [30,60]
      NUM_TEST $(GEOM_minLAT) RANGE [-90,-70]
      NUM_TEST $(GEOM_minLON) RANGE [30,60]
      NUM_TEST $(GEOM_minLAT) RANGE [-90,-70]
      NUM_TEST $(GEOM_maxLON) RANGE [30,60]",<pass>
    <pass> -> FeatureReader_97 [INITIATOR]
FeatureReader_97
    ATTRIBUTES = TIFF,
    ATTR_ACCUM_MODE = Only Use Result
    COMBINE_GEOM = Use Result
    COORDSYS = LL-WGS84
    DATASET = $(FME_MF_DIR_ENCODED)DEM\S90\90s030e_20101117_gmted_dsc300.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S90E60: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-90,-70]
      NUM_TEST $(GEOM_maxLON) RANGE [60,90]
      NUM_TEST $(GEOM_maxLAT) RANGE [-90,-70]
      NUM_TEST $(GEOM_minLON) RANGE [60,90]
      NUM_TEST $(GEOM_minLAT) RANGE [-90,-70]
      NUM_TEST $(GEOM_minLON) RANGE [60,90]
      NUM_TEST $(GEOM_minLAT) RANGE [-90,-70]
      NUM_TEST $(GEOM_maxLON) RANGE [60,90]",<pass>
    <pass> -> FeatureReader_100 [INITIATOR]
FeatureReader_100
    ATTRIBUTES = TIFF,
    ATTR_ACCUM_MODE = Only Use Result
    COMBINE_GEOM = Use Result
    COORDSYS = LL-WGS84
    DATASET = $(FME_MF_DIR_ENCODED)DEM\S90\90s060e_20101117_gmted_dsc300.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S90E90: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-90,-70]
      NUM_TEST $(GEOM_maxLON) RANGE [90,120]
      NUM_TEST $(GEOM_maxLAT) RANGE [-90,-70]
      NUM_TEST $(GEOM_minLON) RANGE [90,120]
      NUM_TEST $(GEOM_minLAT) RANGE [-90,-70]
      NUM_TEST $(GEOM_minLON) RANGE [90,120]
      NUM_TEST $(GEOM_minLAT) RANGE [-90,-70]
      NUM_TEST $(GEOM_maxLON) RANGE [90,120]",<pass>
    <pass> -> FeatureReader_101 [INITIATOR]
FeatureReader_101
    ATTRIBUTES = TIFF,
    ATTR_ACCUM_MODE = Only Use Result
    COMBINE_GEOM = Use Result
    COORDSYS = LL-WGS84
    DATASET = $(FME_MF_DIR_ENCODED)DEM\S90\90s090e_20101117_gmted_dsc300.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S90E120: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-90,-70]
      NUM_TEST $(GEOM_maxLON) RANGE [120,150]
      NUM_TEST $(GEOM_maxLAT) RANGE [-90,-70]
      NUM_TEST $(GEOM_minLON) RANGE [120,150]
      NUM_TEST $(GEOM_minLAT) RANGE [-90,-70]
      NUM_TEST $(GEOM_minLON) RANGE [120,150]
      NUM_TEST $(GEOM_minLAT) RANGE [-90,-70]
      NUM_TEST $(GEOM_maxLON) RANGE [120,150]",<pass>
    <pass> -> FeatureReader_102 [INITIATOR]
FeatureReader_102
    ATTRIBUTES = TIFF,
    ATTR_ACCUM_MODE = Only Use Result
    COMBINE_GEOM = Use Result
    COORDSYS = LL-WGS84
    DATASET = $(FME_MF_DIR_ENCODED)DEM\S90\90s120e_20101117_gmted_dsc300.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S90E150: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-90,-70]
      NUM_TEST $(GEOM_maxLON) RANGE [150,180]
      NUM_TEST $(GEOM_maxLAT) RANGE [-90,-70]
      NUM_TEST $(GEOM_minLON) RANGE [150,180]
      NUM_TEST $(GEOM_minLAT) RANGE [-90,-70]
      NUM_TEST $(GEOM_minLON) RANGE [150,180]
      NUM_TEST $(GEOM_minLAT) RANGE [-90,-70]
      NUM_TEST $(GEOM_maxLON) RANGE [150,180]",<pass>
    <pass> -> FeatureReader_103 [INITIATOR]
FeatureReader_103
    ATTRIBUTES = TIFF,
    ATTR_ACCUM_MODE = Only Use Result
    COMBINE_GEOM = Use Result
    COORDSYS = LL-WGS84
    DATASET = $(FME_MF_DIR_ENCODED)DEM\S90\90s150e_20101117_gmted_dsc300.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S90W30: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-90,-70]
      NUM_TEST $(GEOM_maxLON) RANGE [-30,0]
      NUM_TEST $(GEOM_maxLAT) RANGE [-90,-70]
      NUM_TEST $(GEOM_minLON) RANGE [-30,0]
      NUM_TEST $(GEOM_minLAT) RANGE [-90,-70]
      NUM_TEST $(GEOM_minLON) RANGE [-30,0]
      NUM_TEST $(GEOM_minLAT) RANGE [-90,-70]
      NUM_TEST $(GEOM_maxLON) RANGE [-30,0]",<pass>
    <pass> -> FeatureReader_99 [INITIATOR]
FeatureReader_99
    ATTRIBUTES = TIFF,
    ATTR_ACCUM_MODE = Only Use Result
    COMBINE_GEOM = Use Result
    COORDSYS = LL-WGS84
    DATASET = $(FME_MF_DIR_ENCODED)DEM\S90\90s030w_20101117_gmted_dsc300.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S90W60: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-90,-70]
      NUM_TEST $(GEOM_maxLON) RANGE [-60,-30]
      NUM_TEST $(GEOM_maxLAT) RANGE [-90,-70]
      NUM_TEST $(GEOM_minLON) RANGE [-60,-30]
      NUM_TEST $(GEOM_minLAT) RANGE [-90,-70]
      NUM_TEST $(GEOM_minLON) RANGE [-60,-30]
      NUM_TEST $(GEOM_minLAT) RANGE [-90,-70]
      NUM_TEST $(GEOM_maxLON) RANGE [-60,-30]",<pass>
    <pass> -> FeatureReader_104 [INITIATOR]
FeatureReader_104
    ATTRIBUTES = TIFF,
    ATTR_ACCUM_MODE = Only Use Result
    COMBINE_GEOM = Use Result
    COORDSYS = LL-WGS84
    DATASET = $(FME_MF_DIR_ENCODED)DEM\S90\90s060w_20101117_gmted_dsc300.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
90W90: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-90,-70]
      NUM_TEST $(GEOM_maxLON) RANGE [-90,-60]
      NUM_TEST $(GEOM_maxLAT) RANGE [-90,-70]
      NUM_TEST $(GEOM_minLON) RANGE [-90,-60]
      NUM_TEST $(GEOM_minLAT) RANGE [-90,-70]
      NUM_TEST $(GEOM_minLON) RANGE [-90,-60]
      NUM_TEST $(GEOM_minLAT) RANGE [-90,-70]
      NUM_TEST $(GEOM_maxLON) RANGE [-90,-60]",<pass>
    <pass> -> FeatureReader_105 [INITIATOR]
FeatureReader_105
    ATTRIBUTES = TIFF,
    ATTR_ACCUM_MODE = Only Use Result
    COMBINE_GEOM = Use Result
    COORDSYS = LL-WGS84
    DATASET = $(FME_MF_DIR_ENCODED)DEM\S90\90s090w_20101117_gmted_dsc300.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S90W120: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-90,-70]
      NUM_TEST $(GEOM_maxLON) RANGE [-120,-90]
      NUM_TEST $(GEOM_maxLAT) RANGE [-90,-70]
      NUM_TEST $(GEOM_minLON) RANGE [-120,-90]
      NUM_TEST $(GEOM_minLAT) RANGE [-90,-70]
      NUM_TEST $(GEOM_minLON) RANGE [-120,-90]
      NUM_TEST $(GEOM_minLAT) RANGE [-90,-70]
      NUM_TEST $(GEOM_maxLON) RANGE [-120,-90]",<pass>
    <pass> -> FeatureReader_106 [INITIATOR]
FeatureReader_106
    ATTRIBUTES = TIFF,
    ATTR_ACCUM_MODE = Only Use Result
    COMBINE_GEOM = Use Result
    COORDSYS = LL-WGS84
    DATASET = $(FME_MF_DIR_ENCODED)DEM\S90\90s120w_20101117_gmted_dsc300.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S90W150: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-90,-70]
      NUM_TEST $(GEOM_maxLON) RANGE [-150,-120]
      NUM_TEST $(GEOM_maxLAT) RANGE [-90,-70]
      NUM_TEST $(GEOM_minLON) RANGE [-150,-120]
      NUM_TEST $(GEOM_minLAT) RANGE [-90,-70]
      NUM_TEST $(GEOM_minLON) RANGE [-150,-120]
      NUM_TEST $(GEOM_minLAT) RANGE [-90,-70]
      NUM_TEST $(GEOM_maxLON) RANGE [-150,-120]",<pass>
    <pass> -> FeatureReader_107 [INITIATOR]
FeatureReader_107
    ATTRIBUTES = TIFF,
    ATTR_ACCUM_MODE = Only Use Result
    COMBINE_GEOM = Use Result
    COORDSYS = LL-WGS84
    DATASET = $(FME_MF_DIR_ENCODED)DEM\S90\90s150w_20101117_gmted_dsc300.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
S90W180: TestFilter
    DEFAULT_VALUE = <notpass>
    TEST_LIST:
      "BOOL_OP,COMPOSITE,COMPOSITE_TEST,""""""( 1 AND 2 )
       OR ( 3 AND 4 )
       OR ( 5 AND 6 )
       OR ( 7 AND 8 )"""""",TEST_CLAUSE,NUM_TEST $(GEOM_maxLAT) RANGE [-90,-70]
      NUM_TEST $(GEOM_maxLON) RANGE [-180,-150]
      NUM_TEST $(GEOM_maxLAT) RANGE [-90,-70]
      NUM_TEST $(GEOM_minLON) RANGE [-180,-150]
      NUM_TEST $(GEOM_minLAT) RANGE [-90,-70]
      NUM_TEST $(GEOM_minLON) RANGE [-180,-150]
      NUM_TEST $(GEOM_minLAT) RANGE [-90,-70]
      NUM_TEST $(GEOM_maxLON) RANGE [-180,-150]",<pass>
    <pass> -> FeatureReader_108 [INITIATOR]
FeatureReader_108
    ATTRIBUTES = TIFF,
    ATTR_ACCUM_MODE = Only Use Result
    COMBINE_GEOM = Use Result
    COORDSYS = LL-WGS84
    DATASET = $(FME_MF_DIR_ENCODED)DEM\S90\90s180w_20101117_gmted_dsc300.tif
    FORMAT = TIFF
    INTERACT = <No Spatial Filter>
    OUTPUT_FEATURES_DISPLAY = Schema and Data Features
    TIFF_FEATURE_TYPE_NAME = FORMAT_NAME
    TIFF_READER_META_ATTRIBUTES = fme_dataset fme_basename
    TIFF_USE_SEARCH_ENVELOPE = NO
    TIFF -> RasterMosaicker_2
RasterMosaicker_2
    ACCUM_ATTRS_NAME = Use Attributes From One Feature
    INTERPOLATION_TYPE_NAME = Nearest Neighbor
    MERGE_PALETTES_NAME = Yes
    NODATA_OVERWRITE = No
    OVERLAPPING_VALUES = last
    SNAPPING_TYPE_NAME = Offset
    -> Clipper [CLIPPEE]
Creator
    COORDS = $(GEOM_minLON) $(GEOM_minLAT) $(GEOM_maxLON) $(GEOM_maxLAT)
    COORDSYS = LL-WGS84
    GEOMTYPE = 2D Min/Max Box
    NUM = 1
    CREATED -> Clipper [CLIPPER]
Clipper
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    INSIDE -> DEM_full (writer GEOTIFF_1)

Bookmark: Writer Feature Types
DEM_full (writer GEOTIFF_1)
