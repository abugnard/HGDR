FME workspace Rasterextractor.fmw
Title: Geospatial PDF - Cartographic Output

Parameters:
- DestDataset_JPEG = $(FME_MF_DIR)outputPDF   # Destination JPEG Folder
- x = 1062   # x tile number
- x_2 = 1062   # x tile number
- x_3 = 1062   # x tile number
- x_4 = 1063   # x tile number
- x_5 = 1063   # x tile number
- x_6 = 1063   # x tile number
- x_7 = 1062   # x tile number
- x_8 = 1062   # x tile number
- x_9 = 1062   # x tile number
- y = 723   # y tile number
- y_2 = 724   # y tile number
- y_3 = 725   # y tile number
- y_4 = 723   # y tile number
- y_5 = 724   # y tile number
- y_6 = 725   # y tile number
- y_7 = 723   # y tile number
- y_8 = 723   # y tile number
- y_9 = 723   # y tile number
- zoom = 11
- x_deg = 6.6796875   # longitude 
- x_deg_2 = 6.6796875   # longitude 
- x_deg_3 = 6.6796875   # longitude 
- x_deg_4 = 6.85546875   # longitude 
- x_deg_5 = 6.85546875   # longitude 
- x_deg_6 = 6.85546875   # longitude 
- x_deg_7 = 6.6796875   # longitude 
- x_deg_8 = 6.6796875   # longitude 
- x_deg_9 = 6.6796875   # longitude 
- y_deg = 46.679594465640186   # latitude 
- y_deg_2 = 46.55886030311718   # latitude 
- y_deg_3 = 46.437856895024204   # latitude 
- y_deg_4 = 46.679594465640186   # latitude 
- y_deg_5 = 46.55886030311718   # latitude 
- y_deg_6 = 46.437856895024204   # latitude 
- y_deg_7 = 46.679594465640186   # latitude 
- y_deg_8 = 46.679594465640186   # latitude 
- y_deg_9 = 46.679594465640186   # latitude 
- DestDataset_JPEG2000 = $(FME_MF_DIR)outputPDF   # Destination JPEG 2000 Folder
- min_lon = 6.834747685877928   # bb min lon
- min_lat = 46.43474768587793   # bb min lat
- max_lon = 6.965252314122073   # bb max lon
- max_lat = 46.56525231412207   # bb max lat
- ISO_code = test_6   # Iso code of the extract
- BASEMAPE = http://a.tile.stamen.com/watercolor   # URL of the basemap
- BASEMAPE_ext = .jpg   # extention of the basemap
- DestDataset_PNGRASTER = $(FME_MF_DIR)outputPDF   # Destination PNG (Portable Network Graphics) Folder

Writers:
- JPEG_1: JPEG to $(DestDataset_JPEG)
- JPEG2000_2: JPEG2000 to $(DestDataset_JPEG2000)
- PNGRASTER_1: PNGRASTER to $(DestDataset_PNGRASTER)

Creator_3
    GEOMTYPE = Geometry Object
    NUM = 1
    CREATED -> AttributeCreator
AttributeCreator
    ATTR_TABLE:
      SET_TO x1 = $(x)
      SET_TO y1 = $(y)
      SET_TO x2 = $(x_2)
      SET_TO x3 = $(x_3)
      SET_TO x4 = $(x_4)
      SET_TO x5 = $(x_5)
      SET_TO x6 = $(x_6)
      SET_TO y2 = $(y_2)
      SET_TO y3 = $(y_3)
      SET_TO y4 = $(y_4)
      SET_TO y5 = $(y_5)
      SET_TO y6 = $(y_6)
    -> TestFilter_17
TestFilter_17
    DEFAULT_VALUE = jpg
    TEST_LIST = "BOOL_OP,OR,COMPOSITE_TEST,""""""1"""""",TEST_CLAUSE,TEST $(BASEMAPE_ext) = .png",png
    png -> FeatureReader_2 [INITIATOR]
    jpg -> FeatureReader_11 [INITIATOR]
FeatureReader_2
    ATTR_ACCUM_MODE = Only Use Result
    COMBINE_GEOM = Use Result
    COORDSYS = LL-WGS84
    DATASET = $(BASEMAPE)/$(zoom)/$(x)/$(y).png
    FORMAT = PNGRASTER
    INTERACT = <No Spatial Filter>
    OUTPUT_FEATURES_DISPLAY = Schema and Data Features
    PNGRASTER_GROUP_BY_DATASET = No
    PNGRASTER_READER_META_ATTRIBUTES = fme_dataset fme_basename
    PNGRASTER_USE_SEARCH_ENVELOPE = NO
    <OTHER> -> RasterPaletteResolver
    INITIATOR -> TestFilter
    INITIATOR -> WorkspacePauser
TestFilter
    DEFAULT_VALUE = <UNFILTERED>
    TEST_LIST:
      "BOOL_OP,OR,COMPOSITE_TEST,""""""1 OR 2"""""",TEST_CLAUSE,TEST $(x) != $(x_2)
      TEST $(y) != $(y_2)",<PASSED>
    <PASSED> -> FeatureReader_3 [INITIATOR]
FeatureReader_3
    ATTRIBUTES = PNGRASTER,
    ATTR_ACCUM_MODE = Only Use Result
    COMBINE_GEOM = Use Result
    COORDSYS = LL-WGS84
    DATASET = http://b.tile.stamen.com/terrain-background/$(zoom)/$(x_2)/$(y_2).png
    FORMAT = PNGRASTER
    INTERACT = <No Spatial Filter>
    OUTPUT_FEATURES_DISPLAY = Schema and Data Features
    PNGRASTER_GROUP_BY_DATASET = No
    PNGRASTER_READER_META_ATTRIBUTES = fme_dataset fme_basename
    PNGRASTER_USE_SEARCH_ENVELOPE = NO
    PNGRASTER -> RasterPaletteResolver_2
    INITIATOR -> TestFilter_2
    INITIATOR -> WorkspacePauser_2
TestFilter_2
    DEFAULT_VALUE = <UNFILTERED>
    TEST_LIST:
      "BOOL_OP,COMPOSITE,COMPOSITE_TEST,""""""( 1 OR 2 ) AND (
       3 OR 4 ) AND ( 5 OR 6 )"""""",TEST_CLAUSE,TEST $(x) != $(x_2)
      TEST $(y) != $(y_2)
      TEST $(x) != $(x_3)
      TEST $(y) != $(y_3)
      TEST $(x_2) != $(x_3)
      TEST $(y_2) != $(y_3)",<PASSED>
    <PASSED> -> FeatureReader_4 [INITIATOR]
FeatureReader_4
    ATTRIBUTES = PNGRASTER,
    ATTR_ACCUM_MODE = Only Use Result
    COMBINE_GEOM = Use Result
    COORDSYS = LL-WGS84
    DATASET = http://b.tile.stamen.com/terrain-background/$(zoom)/$(x_3)/$(y_3).png
    FORMAT = PNGRASTER
    INTERACT = <No Spatial Filter>
    OUTPUT_FEATURES_DISPLAY = Schema and Data Features
    PNGRASTER_GROUP_BY_DATASET = No
    PNGRASTER_READER_META_ATTRIBUTES = fme_dataset fme_basename
    PNGRASTER_USE_SEARCH_ENVELOPE = NO
    PNGRASTER -> RasterPaletteResolver_3
    INITIATOR -> TestFilter_4
    INITIATOR -> WorkspacePauser_3
TestFilter_4
    DEFAULT_VALUE = <UNFILTERED>
    TEST_LIST:
      "BOOL_OP,COMPOSITE,COMPOSITE_TEST,""""""( 1 OR 2 ) AND (
       3 OR 4 ) AND ( 5 OR 6 ) AND (
       7 OR 8 ) AND (
       9 OR 10 ) AND (
       11 OR 12 )"""""",TEST_CLAUSE,TEST $(x) != $(x_2)
      TEST $(y) != $(y_2)
      TEST $(x) != $(x_3)
      TEST 403 != $(y_3)
      TEST $(x_2) != $(x_3)
      TEST $(y_2) != $(y_3)
      TEST $(x) != $(x_4)
      TEST $(y) != $(y_4)
      TEST $(x_2) != $(x_4)
      TEST $(y_2) != $(y_4)
      TEST $(x_3) != $(x_4)
      TEST $(y_3) != $(y_4)",<PASSED>
    <PASSED> -> FeatureReader_5 [INITIATOR]
FeatureReader_5
    ATTRIBUTES = PNGRASTER,
    ATTR_ACCUM_MODE = Only Use Result
    COMBINE_GEOM = Use Result
    COORDSYS = LL-WGS84
    DATASET = http://b.tile.stamen.com/terrain-background/$(zoom)/$(x_4)/$(y_4).png
    FORMAT = PNGRASTER
    INTERACT = <No Spatial Filter>
    OUTPUT_FEATURES_DISPLAY = Schema and Data Features
    PNGRASTER_GROUP_BY_DATASET = No
    PNGRASTER_READER_META_ATTRIBUTES = fme_dataset fme_basename
    PNGRASTER_USE_SEARCH_ENVELOPE = NO
    PNGRASTER -> RasterPaletteResolver_4
    INITIATOR -> TestFilter_3
    INITIATOR -> WorkspacePauser_4
RasterPaletteResolver_4
    -> RasterGeoreferencer_4
RasterGeoreferencer_4
    POINTANDANGLE_OR_EXTENTS = Extents
    X_LL_COORD = $(x_deg_4)
    X_LR_COORD = $(x_deg_4)+(360/@pow(2,$(zoom)))
    X_UL_COORD = $(x_deg_4)
    X_UR_COORD = $(x_deg_4)+(360/@pow(2,$(zoom)))
    Y_LL_COORD = $(y_deg_4) - (360/@pow(2,$(zoom)))*@cos(($(y_deg_4)-360/(@pow(2,$(zoom)+1)))*@pi()/180)
    Y_LR_COORD = $(y_deg_4) - (360/@pow(2,$(zoom)))*@cos(($(y_deg_4)-360/(@pow(2,$(zoom)+1)))*@pi()/180)
    Y_UL_COORD = $(y_deg_4)
    Y_UR_COORD = $(y_deg_4)
    -> RasterMosaicker
TestFilter_3
    DEFAULT_VALUE = <UNFILTERED>
    TEST_LIST:
      "BOOL_OP,COMPOSITE,COMPOSITE_TEST,""""""( 1 OR 2 ) AND (
       3 OR 4 ) AND ( 5 OR 6 ) AND (
       7 OR 8 ) AND (
       9 OR 10 ) AND (
       11 OR 12 ) AND ( 13 OR 14 ) AND ( 15 OR 16 ) AND ( 17 OR 18 ) AND ( 19 OR 20 )"""""",TEST_CLAUSE,TEST $(x) != $(x_2)
      TEST $(y) != $(y_2)
      TEST $(x) != $(x_3)
      TEST $(y) != $(y_3)
      TEST $(x_2) != $(x_3)
      TEST $(y_2) != $(y_3)
      TEST $(x) != $(x_4)
      TEST $(y) != $(y_4)
      TEST $(x_2) != $(x_4)
      TEST $(y_2) != $(y_4)
      TEST $(x_3) != $(x_4)
      TEST $(y_3) != $(y_4)
      TEST $(x) != $(x_5)
      TEST $(y) != $(y_5)
      TEST $(x_2) != $(x_5)
      TEST $(y_2) != $(y_5)
      TEST $(x_3) != $(x_5)
      TEST $(y_3) != $(y_5)
      TEST $(x_4) != $(x_5)
      TEST $(y_4) != $(y_5)",<PASSED>
    <PASSED> -> FeatureReader_6 [INITIATOR]
FeatureReader_6
    ATTRIBUTES = PNGRASTER,
    ATTR_ACCUM_MODE = Only Use Result
    COMBINE_GEOM = Use Result
    COORDSYS = LL-WGS84
    DATASET = http://b.tile.stamen.com/terrain-background/$(zoom)/$(x_5)/$(y_5).png
    FORMAT = PNGRASTER
    INTERACT = <No Spatial Filter>
    OUTPUT_FEATURES_DISPLAY = Schema and Data Features
    PNGRASTER_GROUP_BY_DATASET = No
    PNGRASTER_READER_META_ATTRIBUTES = fme_dataset fme_basename
    PNGRASTER_USE_SEARCH_ENVELOPE = NO
    PNGRASTER -> RasterPaletteResolver_5
    INITIATOR -> TestFilter_5
    INITIATOR -> WorkspacePauser_7
RasterPaletteResolver_5
    -> RasterGeoreferencer_5
RasterGeoreferencer_5
    POINTANDANGLE_OR_EXTENTS = Extents
    X_LL_COORD = $(x_deg_5)
    X_LR_COORD = $(x_deg_5)+(360/@pow(2,$(zoom)))
    X_UL_COORD = $(x_deg_5)
    X_UR_COORD = $(x_deg_5)+(360/@pow(2,$(zoom)))
    Y_LL_COORD = $(y_deg_5) - (360/@pow(2,$(zoom)))*@cos(($(y_deg_5)-360/(@pow(2,$(zoom)+1)))*@pi()/180)
    Y_LR_COORD = $(y_deg_5) - (360/@pow(2,$(zoom)))*@cos(($(y_deg_5)-360/(@pow(2,$(zoom)+1)))*@pi()/180)
    Y_UL_COORD = $(y_deg_5)
    Y_UR_COORD = $(y_deg_5)
    -> RasterMosaicker
TestFilter_5
    DEFAULT_VALUE = <UNFILTERED>
    TEST_LIST:
      "BOOL_OP,COMPOSITE,COMPOSITE_TEST,""""""( 1 OR 2 ) AND (
       3 OR 4 ) AND ( 5 OR 6 ) AND (
       7 OR 8 ) AND (
       9 OR 10 ) AND (
       11 OR 12 ) AND ( 13 OR 14 ) AND ( 15 OR 16 ) AND ( 17 OR 18 ) AND ( 19 OR 20 ) AND ( 21 OR 22 ) AND ( 23 OR 24 ) AND ( 25 OR 26 ) AND ( 27 OR 28 ) AND ( 29 OR 30 )"""""",TEST_CLAUSE,TEST $(x) != $(x_2)
      TEST 403 != $(y_2)
      TEST $(x) != $(x_3)
      TEST $(y) != $(y_3)
      TEST $(x_2) != $(x_3)
      TEST $(y_2) != $(y_3)
      TEST $(x) != $(x_4)
      TEST $(y) != $(y_4)
      TEST $(x_2) != $(x_4)
      TEST $(y_2) != $(y_4)
      TEST $(x_3) != $(x_4)
      TEST $(y_3) != $(y_4)
      TEST $(x) != $(x_5)
      TEST $(y) != $(y_5)
      TEST $(x_2) != $(x_5)
      TEST $(y_2) != $(y_5)
      TEST $(x_3) != $(x_5)
      TEST $(y_3) != $(y_5)
      TEST $(x_4) != $(x_5)
      TEST $(y_4) != $(y_5)
      TEST $(x) != $(x_6)
      TEST $(y) != $(y_6)
      TEST $(x_2) != $(x_6)
      TEST $(y_2) != $(y_6)
      TEST $(x_3) != $(x_6)
      TEST $(y_3) != $(y_6)
      TEST $(x_4) != $(x_6)
      TEST $(y_4) != $(y_6)
      TEST $(x_5) != $(x_6)
      TEST $(y_5) != $(y_6)",<PASSED>
    <PASSED> -> FeatureReader_7 [INITIATOR]
FeatureReader_7
    ATTRIBUTES = PNGRASTER,
    ATTR_ACCUM_MODE = Only Use Result
    COMBINE_GEOM = Use Result
    COORDSYS = LL-WGS84
    DATASET = http://b.tile.stamen.com/terrain-background/$(zoom)/$(x_6)/$(y_6).png
    FORMAT = PNGRASTER
    INTERACT = <No Spatial Filter>
    OUTPUT_FEATURES_DISPLAY = Schema and Data Features
    PNGRASTER_GROUP_BY_DATASET = No
    PNGRASTER_READER_META_ATTRIBUTES = fme_dataset fme_basename
    PNGRASTER_USE_SEARCH_ENVELOPE = NO
    PNGRASTER -> RasterPaletteResolver_6
    INITIATOR -> TestFilter_6
    INITIATOR -> WorkspacePauser_5
RasterPaletteResolver_6
    -> RasterGeoreferencer_6
RasterGeoreferencer_6
    POINTANDANGLE_OR_EXTENTS = Extents
    X_LL_COORD = $(x_deg_6)
    X_LR_COORD = $(x_deg_6)+(360/@pow(2,$(zoom)))
    X_UL_COORD = $(x_deg_6)
    X_UR_COORD = $(x_deg_6)+(360/@pow(2,$(zoom)))
    Y_LL_COORD = $(y_deg_6) - (360/@pow(2,$(zoom)))*@cos(($(y_deg_6)-360/(@pow(2,$(zoom)+1)))*@pi()/180)
    Y_LR_COORD = $(y_deg_6) - (360/@pow(2,$(zoom)))*@cos(($(y_deg_6)-360/(@pow(2,$(zoom)+1)))*@pi()/180)
    Y_UL_COORD = $(y_deg_6)
    Y_UR_COORD = $(y_deg_6)
    -> RasterMosaicker
TestFilter_6
    DEFAULT_VALUE = <UNFILTERED>
    TEST_LIST:
      "BOOL_OP,COMPOSITE,COMPOSITE_TEST,""""""( 1 OR 2 ) AND ( 3 OR 4 ) AND ( 5 OR 6 ) AND ( 7 OR 8 ) AND ( 9 OR 10 ) AND ( 11 OR 12 )"""""",TEST_CLAUSE,TEST $(x_7) != $(x)
      TEST $(y_7) != $(y)
      TEST $(x_7) != $(x_2)
      TEST $(y_7) != $(y_2)
      TEST $(x_7) != $(x_3)
      TEST $(y_7) != $(y_3)
      TEST $(x_7) != $(x_4)
      TEST $(y_7) != $(y_4)
      TEST $(x_7) != $(x_5)
      TEST $(y_7) != $(y_5)
      TEST $(x_7) != $(x_6)
      TEST $(y_7) != $(y_6)",<PASSED>
    <PASSED> -> FeatureReader_8 [INITIATOR]
FeatureReader_8
    ATTRIBUTES = PNGRASTER,
    ATTR_ACCUM_MODE = Only Use Result
    COMBINE_GEOM = Use Result
    COORDSYS = LL-WGS84
    DATASET = http://b.tile.stamen.com/terrain-background/$(zoom)/$(x_7)/$(y_7).png
    FORMAT = PNGRASTER
    INTERACT = <No Spatial Filter>
    OUTPUT_FEATURES_DISPLAY = Schema and Data Features
    PNGRASTER_GROUP_BY_DATASET = No
    PNGRASTER_READER_META_ATTRIBUTES = fme_dataset fme_basename
    PNGRASTER_USE_SEARCH_ENVELOPE = NO
    PNGRASTER -> RasterPaletteResolver_7
    INITIATOR -> TestFilter_7
    INITIATOR -> WorkspacePauser_6
RasterPaletteResolver_7
    -> RasterGeoreferencer_7
RasterGeoreferencer_7
    POINTANDANGLE_OR_EXTENTS = Extents
    X_LL_COORD = $(x_deg_7)
    X_LR_COORD = $(x_deg_7)+(360/@pow(2,$(zoom)))
    X_UL_COORD = $(x_deg_7)
    X_UR_COORD = $(x_deg_7)+(360/@pow(2,$(zoom)))
    Y_LL_COORD = $(y_deg_7) - (360/@pow(2,$(zoom)))*@cos(($(y_deg_7)-360/(@pow(2,$(zoom)+1)))*@pi()/180)
    Y_LR_COORD = $(y_deg_7) - (360/@pow(2,$(zoom)))*@cos(($(y_deg_7)-360/(@pow(2,$(zoom)+1)))*@pi()/180)
    Y_UL_COORD = $(y_deg_7)
    Y_UR_COORD = $(y_deg_7)
    -> RasterMosaicker
TestFilter_7
    DEFAULT_VALUE = <UNFILTERED>
    TEST_LIST:
      "BOOL_OP,COMPOSITE,COMPOSITE_TEST,""""""( 1 OR 2 ) AND ( 3 OR 4 ) AND ( 5 OR 6 ) AND ( 7 OR 8 ) AND ( 9 OR 10 ) AND ( 11 OR 12 ) AND ( 13 OR 14 )"""""",TEST_CLAUSE,TEST $(x_8) != $(x)
      TEST $(y_8) != $(y)
      TEST $(x_8) != $(x_2)
      TEST $(y_8) != $(y_2)
      TEST $(x_8) != $(x_3)
      TEST $(y_8) != $(y_3)
      TEST $(x_8) != $(x_4)
      TEST $(y_8) != $(y_4)
      TEST $(x_8) != $(x_5)
      TEST $(y_8) != $(y_5)
      TEST $(x_8) != $(x_6)
      TEST $(y_8) != $(y_6)
      TEST $(x_8) != $(x_7)
      TEST $(y_8) != $(y_7)",<PASSED>
    <PASSED> -> FeatureReader_9 [INITIATOR]
FeatureReader_9
    ATTRIBUTES = PNGRASTER,
    ATTR_ACCUM_MODE = Only Use Result
    COMBINE_GEOM = Use Result
    COORDSYS = LL-WGS84
    DATASET = http://b.tile.stamen.com/terrain-background/$(zoom)/$(x_8)/$(y_8).png
    FORMAT = PNGRASTER
    INTERACT = <No Spatial Filter>
    OUTPUT_FEATURES_DISPLAY = Schema and Data Features
    PNGRASTER_GROUP_BY_DATASET = No
    PNGRASTER_READER_META_ATTRIBUTES = fme_dataset fme_basename
    PNGRASTER_USE_SEARCH_ENVELOPE = NO
    PNGRASTER -> RasterPaletteResolver_8
    INITIATOR -> TestFilter_8
    INITIATOR -> WorkspacePauser_8
RasterPaletteResolver_8
    -> RasterGeoreferencer_8
RasterGeoreferencer_8
    POINTANDANGLE_OR_EXTENTS = Extents
    X_LL_COORD = $(x_deg_8)
    X_LR_COORD = $(x_deg_8)+(360/@pow(2,$(zoom)))
    X_UL_COORD = $(x_deg_8)
    X_UR_COORD = $(x_deg_8)+(360/@pow(2,$(zoom)))
    Y_LL_COORD = $(y_deg_8) - (360/@pow(2,$(zoom)))*@cos(($(y_deg_8)-360/(@pow(2,$(zoom)+1)))*@pi()/180)
    Y_LR_COORD = $(y_deg_8) - (360/@pow(2,$(zoom)))*@cos(($(y_deg_8)-360/(@pow(2,$(zoom)+1)))*@pi()/180)
    Y_UL_COORD = $(y_deg_8)
    Y_UR_COORD = $(y_deg_8)
    -> RasterMosaicker
TestFilter_8
    DEFAULT_VALUE = <UNFILTERED>
    TEST_LIST:
      "BOOL_OP,COMPOSITE,COMPOSITE_TEST,""""""( 1 OR 2 ) AND ( 3 OR 4 ) AND ( 5 OR 6 ) AND ( 7 OR 8 ) AND ( 9 OR 10 ) AND ( 11 OR 12 ) AND ( 13 OR 14 ) AND ( 15 OR 16 )"""""",TEST_CLAUSE,TEST $(x_9) != $(x)
      TEST $(y_9) != $(y)
      TEST $(x_9) != $(x_2)
      TEST $(y_9) != $(y_2)
      TEST $(x_9) != $(x_3)
      TEST $(y_9) != $(y_3)
      TEST $(x_9) != $(x_4)
      TEST $(y_9) != $(y_4)
      TEST $(x_9) != $(x_5)
      TEST $(y_9) != $(y_5)
      TEST $(x_9) != $(x_6)
      TEST $(y_9) != $(y_6)
      TEST $(x_9) != $(x_7)
      TEST $(y_9) != $(y_7)
      TEST $(x_9) != $(x_8)
      TEST $(y_9) != $(y_8)",<PASSED>
    <PASSED> -> FeatureReader_10 [INITIATOR]
FeatureReader_10
    ATTRIBUTES = PNGRASTER,
    ATTR_ACCUM_MODE = Only Use Result
    COMBINE_GEOM = Use Result
    COORDSYS = LL-WGS84
    DATASET = http://b.tile.stamen.com/terrain-background/$(zoom)/$(x_9)/$(y_9).png
    FORMAT = PNGRASTER
    INTERACT = <No Spatial Filter>
    OUTPUT_FEATURES_DISPLAY = Schema and Data Features
    PNGRASTER_GROUP_BY_DATASET = No
    PNGRASTER_READER_META_ATTRIBUTES = fme_dataset fme_basename
    PNGRASTER_USE_SEARCH_ENVELOPE = NO
    PNGRASTER -> RasterPaletteResolver_9
RasterPaletteResolver_9
    -> RasterGeoreferencer_9
RasterGeoreferencer_9
    POINTANDANGLE_OR_EXTENTS = Extents
    X_LL_COORD = $(x_deg_9)
    X_LR_COORD = $(x_deg_9)+(360/@pow(2,$(zoom)))
    X_UL_COORD = $(x_deg_9)
    X_UR_COORD = $(x_deg_9)+(360/@pow(2,$(zoom)))
    Y_LL_COORD = $(y_deg_9) - (360/@pow(2,$(zoom)))*@cos(($(y_deg_9)-360/(@pow(2,$(zoom)+1)))*@pi()/180)
    Y_LR_COORD = $(y_deg_9) - (360/@pow(2,$(zoom)))*@cos(($(y_deg_9)-360/(@pow(2,$(zoom)+1)))*@pi()/180)
    Y_UL_COORD = $(y_deg_9)
    Y_UR_COORD = $(y_deg_9)
    -> RasterMosaicker
WorkspacePauser_8
    Pauser = 10
WorkspacePauser_6
    Pauser = 10
WorkspacePauser_5
    Pauser = 10
WorkspacePauser_7
    Pauser = 10
WorkspacePauser_4
    Pauser = 10
RasterPaletteResolver_3
    -> RasterGeoreferencer_3
RasterGeoreferencer_3
    POINTANDANGLE_OR_EXTENTS = Extents
    X_LL_COORD = $(x_deg_3)
    X_LR_COORD = $(x_deg_3)+(360/@pow(2,$(zoom)))
    X_UL_COORD = $(x_deg_3)
    X_UR_COORD = $(x_deg_3)+(360/@pow(2,$(zoom)))
    Y_LL_COORD = $(y_deg_3) - (360/@pow(2,$(zoom)))*@cos(($(y_deg_3)-360/(@pow(2,$(zoom)+1)))*@pi()/180)
    Y_LR_COORD = $(y_deg_3) - (360/@pow(2,$(zoom)))*@cos(($(y_deg_3)-360/(@pow(2,$(zoom)+1)))*@pi()/180)
    Y_UL_COORD = $(y_deg_3)
    Y_UR_COORD = $(y_deg_3)
    -> RasterMosaicker
WorkspacePauser_3
    Pauser = 10
WorkspacePauser_2
    Pauser = 10
RasterPaletteResolver_2
    -> RasterGeoreferencer_2
RasterGeoreferencer_2
    POINTANDANGLE_OR_EXTENTS = Extents
    X_LL_COORD = $(x_deg_2)
    X_LR_COORD = $(x_deg_2)+(360/@pow(2,$(zoom)))
    X_UL_COORD = $(x_deg_2)
    X_UR_COORD = $(x_deg_2)+(360/@pow(2,$(zoom)))
    Y_LL_COORD = $(y_deg_2) - (360/@pow(2,$(zoom)))*@cos(($(y_deg_2)-360/(@pow(2,$(zoom)+1)))*@pi()/180)
    Y_LR_COORD = $(y_deg_2) - (360/@pow(2,$(zoom)))*@cos(($(y_deg_2)-360/(@pow(2,$(zoom)+1)))*@pi()/180)
    Y_UL_COORD = $(y_deg_2)
    Y_UR_COORD = $(y_deg_2)
    -> RasterMosaicker
WorkspacePauser
    Pauser = 10
RasterPaletteResolver
    -> RasterGeoreferencer
RasterGeoreferencer
    POINTANDANGLE_OR_EXTENTS = Extents
    X_LL_COORD = $(x_deg)
    X_LR_COORD = $(x_deg)+(360/@pow(2,$(zoom)))
    X_UL_COORD = $(x_deg)
    X_UR_COORD = $(x_deg)+(360/@pow(2,$(zoom)))
    Y_LL_COORD = $(y_deg) - (360/@pow(2,$(zoom)))*@cos(($(y_deg)-360/(@pow(2,$(zoom)+1)))*@pi()/180)
    Y_LR_COORD = $(y_deg) - (360/@pow(2,$(zoom)))*@cos(($(y_deg)-360/(@pow(2,$(zoom)+1)))*@pi()/180)
    Y_UL_COORD = $(y_deg)
    Y_UR_COORD = $(y_deg)
    -> RasterMosaicker
RasterMosaicker
    ACCUM_ATTRS_NAME = Use Attributes From One Feature
    INTERPOLATION_TYPE_NAME = Nearest Neighbor
    MERGE_PALETTES_NAME = Yes
    NODATA_OVERWRITE = No
    OVERLAPPING_VALUES = last
    SNAPPING_TYPE_NAME = Offset
    -> Clipper [CLIPPEE]
FeatureReader_11
    ATTR_ACCUM_MODE = Only Use Result
    COMBINE_GEOM = Use Result
    COORDSYS = LL-WGS84
    DATASET = $(BASEMAPE)/$(zoom)/@Value(x1)/@Value(y1).jpg
    FORMAT = JPEG
    INTERACT = <No Spatial Filter>
    JPEG_ALL_ATTRS_STARTING_WITH_EXIF_ARE_FORMAT_ATTRS = YES
    JPEG_APPLY_EXIF_ORIENTATION = Yes
    JPEG_APPLY_GCPS = NO
    JPEG_GROUP_BY_DATASET = No
    JPEG_READER_META_ATTRIBUTES = fme_dataset fme_basename
    JPEG_USE_SEARCH_ENVELOPE = NO
    OUTPUT_FEATURES_DISPLAY = Schema and Data Features
    <OTHER> -> RasterPaletteResolver_10
    INITIATOR -> TestFilter_9
TestFilter_9
    DEFAULT_VALUE = <UNFILTERED>
    TEST_LIST:
      "BOOL_OP,OR,COMPOSITE_TEST,""""""1 OR 2"""""",TEST_CLAUSE,TEST $(x) != $(x_2)
      TEST $(y) != $(y_2)",<PASSED>
    <PASSED> -> FeatureReader_12 [INITIATOR]
FeatureReader_12
    ATTR_ACCUM_MODE = Only Use Result
    COMBINE_GEOM = Use Result
    COORDSYS = LL-WGS84
    DATASET = $(BASEMAPE)/$(zoom)/@Value(x2)/@Value(y2).jpg
    FORMAT = JPEG
    INTERACT = <No Spatial Filter>
    JPEG_ALL_ATTRS_STARTING_WITH_EXIF_ARE_FORMAT_ATTRS = YES
    JPEG_APPLY_EXIF_ORIENTATION = Yes
    JPEG_APPLY_GCPS = NO
    JPEG_GROUP_BY_DATASET = No
    JPEG_READER_META_ATTRIBUTES = fme_dataset fme_basename
    JPEG_USE_SEARCH_ENVELOPE = NO
    OUTPUT_FEATURES_DISPLAY = Schema and Data Features
    <OTHER> -> RasterPaletteResolver_11
    INITIATOR -> TestFilter_10
TestFilter_10
    DEFAULT_VALUE = <UNFILTERED>
    TEST_LIST:
      "BOOL_OP,COMPOSITE,COMPOSITE_TEST,""""""( 1 OR 2 ) AND (
       3 OR 4 ) AND ( 5 OR 6 )"""""",TEST_CLAUSE,TEST $(x) != $(x_2)
      TEST $(y) != $(y_2)
      TEST $(x) != $(x_3)
      TEST $(y) != $(y_3)
      TEST $(x_2) != $(x_3)
      TEST $(y_2) != $(y_3)",<PASSED>
    <PASSED> -> FeatureReader_13 [INITIATOR]
FeatureReader_13
    ATTR_ACCUM_MODE = Only Use Result
    COMBINE_GEOM = Use Result
    COORDSYS = LL-WGS84
    DATASET = $(BASEMAPE)/$(zoom)/@Value(x3)/@Value(y3).jpg
    FORMAT = JPEG
    INTERACT = <No Spatial Filter>
    JPEG_ALL_ATTRS_STARTING_WITH_EXIF_ARE_FORMAT_ATTRS = YES
    JPEG_APPLY_EXIF_ORIENTATION = Yes
    JPEG_APPLY_GCPS = NO
    JPEG_GROUP_BY_DATASET = No
    JPEG_READER_META_ATTRIBUTES = fme_dataset fme_basename
    JPEG_USE_SEARCH_ENVELOPE = NO
    OUTPUT_FEATURES_DISPLAY = Schema and Data Features
    <OTHER> -> RasterPaletteResolver_12
    INITIATOR -> TestFilter_11
TestFilter_11
    DEFAULT_VALUE = <UNFILTERED>
    TEST_LIST:
      "BOOL_OP,COMPOSITE,COMPOSITE_TEST,""""""( 1 OR 2 ) AND (
       3 OR 4 ) AND ( 5 OR 6 ) AND (
       7 OR 8 ) AND (
       9 OR 10 ) AND (
       11 OR 12 )"""""",TEST_CLAUSE,TEST $(x) != $(x_2)
      TEST $(y) != $(y_2)
      TEST $(x) != $(x_3)
      TEST 403 != $(y_3)
      TEST $(x_2) != $(x_3)
      TEST $(y_2) != $(y_3)
      TEST $(x) != $(x_4)
      TEST $(y) != $(y_4)
      TEST $(x_2) != $(x_4)
      TEST $(y_2) != $(y_4)
      TEST $(x_3) != $(x_4)
      TEST $(y_3) != $(y_4)",<PASSED>
    <PASSED> -> FeatureReader_14 [INITIATOR]
FeatureReader_14
    ATTR_ACCUM_MODE = Only Use Result
    COMBINE_GEOM = Use Result
    COORDSYS = LL-WGS84
    DATASET = $(BASEMAPE)/$(zoom)/@Value(x4)/@Value(y4).jpg
    FORMAT = JPEG
    INTERACT = <No Spatial Filter>
    JPEG_ALL_ATTRS_STARTING_WITH_EXIF_ARE_FORMAT_ATTRS = YES
    JPEG_APPLY_EXIF_ORIENTATION = Yes
    JPEG_APPLY_GCPS = NO
    JPEG_GROUP_BY_DATASET = No
    JPEG_READER_META_ATTRIBUTES = fme_dataset fme_basename
    JPEG_USE_SEARCH_ENVELOPE = NO
    OUTPUT_FEATURES_DISPLAY = Schema and Data Features
    <OTHER> -> RasterPaletteResolver_13
    INITIATOR -> TestFilter_12
RasterPaletteResolver_13
    -> RasterGeoreferencer_13
RasterGeoreferencer_13
    POINTANDANGLE_OR_EXTENTS = Extents
    X_LL_COORD = $(x_deg_4)
    X_LR_COORD = $(x_deg_4)+(360/@pow(2,$(zoom)))
    X_UL_COORD = $(x_deg_4)
    X_UR_COORD = $(x_deg_4)+(360/@pow(2,$(zoom)))
    Y_LL_COORD = $(y_deg_4) - (360/@pow(2,$(zoom)))*@cos(($(y_deg_4)-360/(@pow(2,$(zoom)+1)))*@pi()/180)
    Y_LR_COORD = $(y_deg_4) - (360/@pow(2,$(zoom)))*@cos(($(y_deg_4)-360/(@pow(2,$(zoom)+1)))*@pi()/180)
    Y_UL_COORD = $(y_deg_4)
    Y_UR_COORD = $(y_deg_4)
    -> RasterMosaicker_2
TestFilter_12
    DEFAULT_VALUE = <UNFILTERED>
    TEST_LIST:
      "BOOL_OP,COMPOSITE,COMPOSITE_TEST,""""""( 1 OR 2 ) AND (
       3 OR 4 ) AND ( 5 OR 6 ) AND (
       7 OR 8 ) AND (
       9 OR 10 ) AND (
       11 OR 12 ) AND ( 13 OR 14 ) AND ( 15 OR 16 ) AND ( 17 OR 18 ) AND ( 19 OR 20 )"""""",TEST_CLAUSE,TEST $(x) != $(x_2)
      TEST $(y) != $(y_2)
      TEST $(x) != $(x_3)
      TEST $(y) != $(y_3)
      TEST $(x_2) != $(x_3)
      TEST $(y_2) != $(y_3)
      TEST $(x) != $(x_4)
      TEST $(y) != $(y_4)
      TEST $(x_2) != $(x_4)
      TEST $(y_2) != $(y_4)
      TEST $(x_3) != $(x_4)
      TEST $(y_3) != $(y_4)
      TEST $(x) != $(x_5)
      TEST $(y) != $(y_5)
      TEST $(x_2) != $(x_5)
      TEST $(y_2) != $(y_5)
      TEST $(x_3) != $(x_5)
      TEST $(y_3) != $(y_5)
      TEST $(x_4) != $(x_5)
      TEST $(y_4) != $(y_5)",<PASSED>
    <PASSED> -> FeatureReader_15 [INITIATOR]
FeatureReader_15
    ATTR_ACCUM_MODE = Only Use Result
    COMBINE_GEOM = Use Result
    COORDSYS = LL-WGS84
    DATASET = $(BASEMAPE)/$(zoom)/@Value(x5)/@Value(y5).jpg
    FORMAT = JPEG
    INTERACT = <No Spatial Filter>
    JPEG_ALL_ATTRS_STARTING_WITH_EXIF_ARE_FORMAT_ATTRS = YES
    JPEG_APPLY_EXIF_ORIENTATION = Yes
    JPEG_APPLY_GCPS = NO
    JPEG_GROUP_BY_DATASET = No
    JPEG_READER_META_ATTRIBUTES = fme_dataset fme_basename
    JPEG_USE_SEARCH_ENVELOPE = NO
    OUTPUT_FEATURES_DISPLAY = Schema and Data Features
    <OTHER> -> RasterPaletteResolver_14
    INITIATOR -> TestFilter_13
RasterPaletteResolver_14
    -> RasterGeoreferencer_14
RasterGeoreferencer_14
    POINTANDANGLE_OR_EXTENTS = Extents
    X_LL_COORD = $(x_deg_5)
    X_LR_COORD = $(x_deg_5)+(360/@pow(2,$(zoom)))
    X_UL_COORD = $(x_deg_5)
    X_UR_COORD = $(x_deg_5)+(360/@pow(2,$(zoom)))
    Y_LL_COORD = $(y_deg_5) - (360/@pow(2,$(zoom)))*@cos(($(y_deg_5)-360/(@pow(2,$(zoom)+1)))*@pi()/180)
    Y_LR_COORD = $(y_deg_5) - (360/@pow(2,$(zoom)))*@cos(($(y_deg_5)-360/(@pow(2,$(zoom)+1)))*@pi()/180)
    Y_UL_COORD = $(y_deg_5)
    Y_UR_COORD = $(y_deg_5)
    -> RasterMosaicker_2
TestFilter_13
    DEFAULT_VALUE = <UNFILTERED>
    TEST_LIST:
      "BOOL_OP,COMPOSITE,COMPOSITE_TEST,""""""( 1 OR 2 ) AND (
       3 OR 4 ) AND ( 5 OR 6 ) AND (
       7 OR 8 ) AND (
       9 OR 10 ) AND (
       11 OR 12 ) AND ( 13 OR 14 ) AND ( 15 OR 16 ) AND ( 17 OR 18 ) AND ( 19 OR 20 ) AND ( 21 OR 22 ) AND ( 23 OR 24 ) AND ( 25 OR 26 ) AND ( 27 OR 28 ) AND ( 29 OR 30 )"""""",TEST_CLAUSE,TEST $(x) != $(x_2)
      TEST 403 != $(y_2)
      TEST $(x) != $(x_3)
      TEST $(y) != $(y_3)
      TEST $(x_2) != $(x_3)
      TEST $(y_2) != $(y_3)
      TEST $(x) != $(x_4)
      TEST $(y) != $(y_4)
      TEST $(x_2) != $(x_4)
      TEST $(y_2) != $(y_4)
      TEST $(x_3) != $(x_4)
      TEST $(y_3) != $(y_4)
      TEST $(x) != $(x_5)
      TEST $(y) != $(y_5)
      TEST $(x_2) != $(x_5)
      TEST $(y_2) != $(y_5)
      TEST $(x_3) != $(x_5)
      TEST $(y_3) != $(y_5)
      TEST $(x_4) != $(x_5)
      TEST $(y_4) != $(y_5)
      TEST $(x) != $(x_6)
      TEST $(y) != $(y_6)
      TEST $(x_2) != $(x_6)
      TEST $(y_2) != $(y_6)
      TEST $(x_3) != $(x_6)
      TEST $(y_3) != $(y_6)
      TEST $(x_4) != $(x_6)
      TEST $(y_4) != $(y_6)
      TEST $(x_5) != $(x_6)
      TEST $(y_5) != $(y_6)",<PASSED>
    <PASSED> -> FeatureReader_16 [INITIATOR]
FeatureReader_16
    ATTR_ACCUM_MODE = Only Use Result
    COMBINE_GEOM = Use Result
    COORDSYS = LL-WGS84
    DATASET = $(BASEMAPE)/$(zoom)/@Value(x6)/@Value(y6).jpg
    FORMAT = JPEG
    INTERACT = <No Spatial Filter>
    JPEG_ALL_ATTRS_STARTING_WITH_EXIF_ARE_FORMAT_ATTRS = YES
    JPEG_APPLY_EXIF_ORIENTATION = Yes
    JPEG_APPLY_GCPS = NO
    JPEG_GROUP_BY_DATASET = No
    JPEG_READER_META_ATTRIBUTES = fme_dataset fme_basename
    JPEG_USE_SEARCH_ENVELOPE = NO
    OUTPUT_FEATURES_DISPLAY = Schema and Data Features
    <OTHER> -> RasterPaletteResolver_15
    INITIATOR -> TestFilter_14
RasterPaletteResolver_15
    -> RasterGeoreferencer_15
RasterGeoreferencer_15
    POINTANDANGLE_OR_EXTENTS = Extents
    X_LL_COORD = $(x_deg_6)
    X_LR_COORD = $(x_deg_6)+(360/@pow(2,$(zoom)))
    X_UL_COORD = $(x_deg_6)
    X_UR_COORD = $(x_deg_6)+(360/@pow(2,$(zoom)))
    Y_LL_COORD = $(y_deg_6) - (360/@pow(2,$(zoom)))*@cos(($(y_deg_6)-360/(@pow(2,$(zoom)+1)))*@pi()/180)
    Y_LR_COORD = $(y_deg_6) - (360/@pow(2,$(zoom)))*@cos(($(y_deg_6)-360/(@pow(2,$(zoom)+1)))*@pi()/180)
    Y_UL_COORD = $(y_deg_6)
    Y_UR_COORD = $(y_deg_6)
    -> RasterMosaicker_2
TestFilter_14
    DEFAULT_VALUE = <UNFILTERED>
    TEST_LIST:
      "BOOL_OP,COMPOSITE,COMPOSITE_TEST,""""""( 1 OR 2 ) AND ( 3 OR 4 ) AND ( 5 OR 6 ) AND ( 7 OR 8 ) AND ( 9 OR 10 ) AND ( 11 OR 12 )"""""",TEST_CLAUSE,TEST $(x_7) != $(x)
      TEST $(y_7) != $(y)
      TEST $(x_7) != $(x_2)
      TEST $(y_7) != $(y_2)
      TEST $(x_7) != $(x_3)
      TEST $(y_7) != $(y_3)
      TEST $(x_7) != $(x_4)
      TEST $(y_7) != $(y_4)
      TEST $(x_7) != $(x_5)
      TEST $(y_7) != $(y_5)
      TEST $(x_7) != $(x_6)
      TEST $(y_7) != $(y_6)",<PASSED>
    <PASSED> -> FeatureReader_17 [INITIATOR]
FeatureReader_17
    ATTRIBUTES = JPEG,
    ATTR_ACCUM_MODE = Only Use Result
    COMBINE_GEOM = Use Result
    COORDSYS = LL-WGS84
    DATASET = $(BASEMAPE)/$(zoom)/$(x_7)/$(y_7).jpg
    FORMAT = JPEG
    INTERACT = <No Spatial Filter>
    JPEG_ALL_ATTRS_STARTING_WITH_EXIF_ARE_FORMAT_ATTRS = YES
    JPEG_APPLY_EXIF_ORIENTATION = Yes
    JPEG_APPLY_GCPS = NO
    JPEG_GROUP_BY_DATASET = No
    JPEG_READER_META_ATTRIBUTES = fme_dataset fme_basename
    JPEG_USE_SEARCH_ENVELOPE = NO
    OUTPUT_FEATURES_DISPLAY = Schema and Data Features
    JPEG -> RasterPaletteResolver_16
    INITIATOR -> TestFilter_15
RasterPaletteResolver_16
    -> RasterGeoreferencer_16
RasterGeoreferencer_16
    POINTANDANGLE_OR_EXTENTS = Extents
    X_LL_COORD = $(x_deg_7)
    X_LR_COORD = $(x_deg_7)+(360/@pow(2,$(zoom)))
    X_UL_COORD = $(x_deg_7)
    X_UR_COORD = $(x_deg_7)+(360/@pow(2,$(zoom)))
    Y_LL_COORD = $(y_deg_7) - (360/@pow(2,$(zoom)))*@cos(($(y_deg_7)-360/(@pow(2,$(zoom)+1)))*@pi()/180)
    Y_LR_COORD = $(y_deg_7) - (360/@pow(2,$(zoom)))*@cos(($(y_deg_7)-360/(@pow(2,$(zoom)+1)))*@pi()/180)
    Y_UL_COORD = $(y_deg_7)
    Y_UR_COORD = $(y_deg_7)
    -> RasterMosaicker_2
TestFilter_15
    DEFAULT_VALUE = <UNFILTERED>
    TEST_LIST:
      "BOOL_OP,COMPOSITE,COMPOSITE_TEST,""""""( 1 OR 2 ) AND ( 3 OR 4 ) AND ( 5 OR 6 ) AND ( 7 OR 8 ) AND ( 9 OR 10 ) AND ( 11 OR 12 ) AND ( 13 OR 14 )"""""",TEST_CLAUSE,TEST $(x_8) != $(x)
      TEST $(y_8) != $(y)
      TEST $(x_8) != $(x_2)
      TEST $(y_8) != $(y_2)
      TEST $(x_8) != $(x_3)
      TEST $(y_8) != $(y_3)
      TEST $(x_8) != $(x_4)
      TEST $(y_8) != $(y_4)
      TEST $(x_8) != $(x_5)
      TEST $(y_8) != $(y_5)
      TEST $(x_8) != $(x_6)
      TEST $(y_8) != $(y_6)
      TEST $(x_8) != $(x_7)
      TEST $(y_8) != $(y_7)",<PASSED>
    <PASSED> -> FeatureReader_18 [INITIATOR]
FeatureReader_18
    ATTRIBUTES = JPEG,
    ATTR_ACCUM_MODE = Only Use Result
    COMBINE_GEOM = Use Result
    COORDSYS = LL-WGS84
    DATASET = $(BASEMAPE)/$(zoom)/$(x_8)/$(y_8).jpg
    FORMAT = JPEG
    INTERACT = <No Spatial Filter>
    JPEG_ALL_ATTRS_STARTING_WITH_EXIF_ARE_FORMAT_ATTRS = YES
    JPEG_APPLY_EXIF_ORIENTATION = Yes
    JPEG_APPLY_GCPS = NO
    JPEG_GROUP_BY_DATASET = No
    JPEG_READER_META_ATTRIBUTES = fme_dataset fme_basename
    JPEG_USE_SEARCH_ENVELOPE = NO
    OUTPUT_FEATURES_DISPLAY = Schema and Data Features
    JPEG -> RasterPaletteResolver_17
    INITIATOR -> TestFilter_16
RasterPaletteResolver_17
    -> RasterGeoreferencer_17
RasterGeoreferencer_17
    POINTANDANGLE_OR_EXTENTS = Extents
    X_LL_COORD = $(x_deg_8)
    X_LR_COORD = $(x_deg_8)+(360/@pow(2,$(zoom)))
    X_UL_COORD = $(x_deg_8)
    X_UR_COORD = $(x_deg_8)+(360/@pow(2,$(zoom)))
    Y_LL_COORD = $(y_deg_8) - (360/@pow(2,$(zoom)))*@cos(($(y_deg_8)-360/(@pow(2,$(zoom)+1)))*@pi()/180)
    Y_LR_COORD = $(y_deg_8) - (360/@pow(2,$(zoom)))*@cos(($(y_deg_8)-360/(@pow(2,$(zoom)+1)))*@pi()/180)
    Y_UL_COORD = $(y_deg_8)
    Y_UR_COORD = $(y_deg_8)
    -> RasterMosaicker_2
TestFilter_16
    DEFAULT_VALUE = <UNFILTERED>
    TEST_LIST:
      "BOOL_OP,COMPOSITE,COMPOSITE_TEST,""""""( 1 OR 2 ) AND ( 3 OR 4 ) AND ( 5 OR 6 ) AND ( 7 OR 8 ) AND ( 9 OR 10 ) AND ( 11 OR 12 ) AND ( 13 OR 14 ) AND ( 15 OR 16 )"""""",TEST_CLAUSE,TEST $(x_9) != $(x)
      TEST $(y_9) != $(y)
      TEST $(x_9) != $(x_2)
      TEST $(y_9) != $(y_2)
      TEST $(x_9) != $(x_3)
      TEST $(y_9) != $(y_3)
      TEST $(x_9) != $(x_4)
      TEST $(y_9) != $(y_4)
      TEST $(x_9) != $(x_5)
      TEST $(y_9) != $(y_5)
      TEST $(x_9) != $(x_6)
      TEST $(y_9) != $(y_6)
      TEST $(x_9) != $(x_7)
      TEST $(y_9) != $(y_7)
      TEST $(x_9) != $(x_8)
      TEST $(y_9) != $(y_8)",<PASSED>
    <PASSED> -> FeatureReader_19 [INITIATOR]
FeatureReader_19
    ATTRIBUTES = JPEG,
    ATTR_ACCUM_MODE = Only Use Result
    COMBINE_GEOM = Use Result
    COORDSYS = LL-WGS84
    DATASET = $(BASEMAPE)/$(zoom)/$(x_9)/$(y_9).jpg
    FORMAT = JPEG
    INTERACT = <No Spatial Filter>
    JPEG_ALL_ATTRS_STARTING_WITH_EXIF_ARE_FORMAT_ATTRS = YES
    JPEG_APPLY_EXIF_ORIENTATION = Yes
    JPEG_APPLY_GCPS = NO
    JPEG_GROUP_BY_DATASET = No
    JPEG_READER_META_ATTRIBUTES = fme_dataset fme_basename
    JPEG_USE_SEARCH_ENVELOPE = NO
    OUTPUT_FEATURES_DISPLAY = Schema and Data Features
    JPEG -> RasterPaletteResolver_18
RasterPaletteResolver_18
    -> RasterGeoreferencer_18
RasterGeoreferencer_18
    POINTANDANGLE_OR_EXTENTS = Extents
    X_LL_COORD = $(x_deg_9)
    X_LR_COORD = $(x_deg_9)+(360/@pow(2,$(zoom)))
    X_UL_COORD = $(x_deg_9)
    X_UR_COORD = $(x_deg_9)+(360/@pow(2,$(zoom)))
    Y_LL_COORD = $(y_deg_9) - (360/@pow(2,$(zoom)))*@cos(($(y_deg_9)-360/(@pow(2,$(zoom)+1)))*@pi()/180)
    Y_LR_COORD = $(y_deg_9) - (360/@pow(2,$(zoom)))*@cos(($(y_deg_9)-360/(@pow(2,$(zoom)+1)))*@pi()/180)
    Y_UL_COORD = $(y_deg_9)
    Y_UR_COORD = $(y_deg_9)
    -> RasterMosaicker_2
RasterPaletteResolver_12
    -> RasterGeoreferencer_12
RasterGeoreferencer_12
    POINTANDANGLE_OR_EXTENTS = Extents
    X_LL_COORD = $(x_deg_3)
    X_LR_COORD = $(x_deg_3)+(360/@pow(2,$(zoom)))
    X_UL_COORD = $(x_deg_3)
    X_UR_COORD = $(x_deg_3)+(360/@pow(2,$(zoom)))
    Y_LL_COORD = $(y_deg_3) - (360/@pow(2,$(zoom)))*@cos(($(y_deg_3)-360/(@pow(2,$(zoom)+1)))*@pi()/180)
    Y_LR_COORD = $(y_deg_3) - (360/@pow(2,$(zoom)))*@cos(($(y_deg_3)-360/(@pow(2,$(zoom)+1)))*@pi()/180)
    Y_UL_COORD = $(y_deg_3)
    Y_UR_COORD = $(y_deg_3)
    -> RasterMosaicker_2
RasterPaletteResolver_11
    -> RasterGeoreferencer_11
RasterGeoreferencer_11
    POINTANDANGLE_OR_EXTENTS = Extents
    X_LL_COORD = $(x_deg_2)
    X_LR_COORD = $(x_deg_2)+(360/@pow(2,$(zoom)))
    X_UL_COORD = $(x_deg_2)
    X_UR_COORD = $(x_deg_2)+(360/@pow(2,$(zoom)))
    Y_LL_COORD = $(y_deg_2) - (360/@pow(2,$(zoom)))*@cos(($(y_deg_2)-360/(@pow(2,$(zoom)+1)))*@pi()/180)
    Y_LR_COORD = $(y_deg_2) - (360/@pow(2,$(zoom)))*@cos(($(y_deg_2)-360/(@pow(2,$(zoom)+1)))*@pi()/180)
    Y_UL_COORD = $(y_deg_2)
    Y_UR_COORD = $(y_deg_2)
    -> RasterMosaicker_2
RasterPaletteResolver_10
    -> RasterGeoreferencer_10
RasterGeoreferencer_10
    POINTANDANGLE_OR_EXTENTS = Extents
    X_LL_COORD = $(x_deg)
    X_LR_COORD = $(x_deg)+(360/@pow(2,$(zoom)))
    X_UL_COORD = $(x_deg)
    X_UR_COORD = $(x_deg)+(360/@pow(2,$(zoom)))
    Y_LL_COORD = $(y_deg) - (360/@pow(2,$(zoom)))*@cos(($(y_deg)-360/(@pow(2,$(zoom)+1)))*@pi()/180)
    Y_LR_COORD = $(y_deg) - (360/@pow(2,$(zoom)))*@cos(($(y_deg)-360/(@pow(2,$(zoom)+1)))*@pi()/180)
    Y_UL_COORD = $(y_deg)
    Y_UR_COORD = $(y_deg)
    -> RasterMosaicker_2
RasterMosaicker_2
    ACCUM_ATTRS_NAME = Use Attributes From One Feature
    INTERPOLATION_TYPE_NAME = Nearest Neighbor
    MERGE_PALETTES_NAME = Yes
    NODATA_OVERWRITE = No
    OVERLAPPING_VALUES = last
    SNAPPING_TYPE_NAME = Offset
    -> Clipper_2 [CLIPPEE]
Creator
    COORDS = $(max_lon) $(max_lat) $(max_lon) $(min_lat) $(min_lon) $(min_lat) $(min_lon) $(max_lat) $(max_lon) $(max_lat)
    COORDSYS = LL-WGS84
    GEOMTYPE = 2D Coordinate List
    NUM = 1
    CREATED -> Clipper [CLIPPER]
Clipper
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    INSIDE -> JPEG2000 (writer JPEG2000_2)
    INSIDE -> Raster100 (writer PNGRASTER_1)
Raster100 (writer PNGRASTER_1)
    attributes: _clipped char(200)
JPEG2000 (writer JPEG2000_2)
Creator_4
    COORDS = $(max_lon) $(max_lat) $(max_lon) $(min_lat) $(min_lon) $(min_lat) $(min_lon) $(max_lat) $(max_lon) $(max_lat)
    COORDSYS = LL-WGS84
    GEOMTYPE = 2D Coordinate List
    NUM = 1
    CREATED -> Clipper_2 [CLIPPER]
Clipper_2
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    INSIDE -> JPEG200000 (writer JPEG2000_2)
    INSIDE -> Raster1 (writer PNGRASTER_1)
Raster1 (writer PNGRASTER_1)
    attributes: _clipped char(200)
JPEG200000 (writer JPEG2000_2)

FME custom transformer WorkspacePauser
This transformer allows to pause a workspace at any specific place in the process. Just connect any transformer/reader to this transformer and set the puasing time (in seconds).
Pausing Time in Seconds.

Parameters:
- Pauser = 10   # Pausing time (Seconds)

Input (input)
    -> Counter
Counter
    CNT_ATTR = _count
    DOMAIN = counterPause
    SCOPE = Local
    START = 0
    -> PythonCaller
PythonCaller
    PYTHONSOURCE:
      import fme
      import fmeobjects
      import time

      # Template Function interface:
      # When using this function, make sure its name is set as the value of
      # the 'Class or Function to Process Features' transformer parameter

      def processFeature(feature):

           PauseTime = $(Pauser)
           Break = feature.getAttribute('_count')
           if int(Break) == 0:
              time.sleep(int(PauseTime))
           else:

              pass
    PYTHONSYMBOL = processFeature
