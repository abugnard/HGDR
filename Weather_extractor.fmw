FME workspace Weather_extractor.fmw

Parameters:
- DestDataset_CSV2 =
- DestDataset_PNGRASTER =
- GEOM =
- ISO3 =

Writers:
- PNGRASTER_1: PNGRASTER to $(DestDataset_PNGRASTER)
- CSV2_1: CSV2 to $(DestDataset_CSV2)

Creator_2
    COORDS = $(GEOM)
    COORDSYS = LL-WGS84
    GEOMTYPE = 2D Min/Max Box
    NUM = 1
    CREATED -> CenterPointExtractor
    CREATED -> FeatureReader [INITIATOR]
CenterPointExtractor
    CENTX = _inside_x
    CENTY = _inside_y
    EXTRACTIONMODE = CENTER
    -> HTTPCaller
    -> FeatureJoiner_3 [RIGHT]
HTTPCaller
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://api.openweathermap.org/data/2.5/forecast?lat=@Value(_inside_y)&lon=@Value(_inside_x)&appid=beeb9ce4829f91765be3060efde0af4c
    TRANSFER_TIMEOUT_LENGTH = 90
    USE_COOKIES = No
    VERIFY_SSL_CERTIFICATES = Yes
    -> AttributeKeeper
Note: https://community.safe.com/s/article/json-transformations
AttributeKeeper
    CREATE_BULK_MODE_FEATURES = NO
    KEEP_ATTRS = _response_body
    -> JSONFlattener
JSONFlattener
    ERROR_LIST_ATTR = _json_error
    JSON_DOCUMENT = @Value(_response_body)
    READ_FROM_FILE = NO
    RECURSIVE = Yes
    -> StringReplacer_9
StringReplacer_9
    CASE = NO
    FIND_TEXT = "snow":{"3h"
    NO_MATCH = _FME_NO_OP_
    REGEXP = NO
    REPLACE_TEXT = "snow":{"3h_s"
    SRC_ATTRS = _response_body
    -> JSONFragmenter
JSONFragmenter
    EXPLODE_FORMAT = JSON
    EXTRACT_ATTR = No
    JSON_ATTR = _response_body
    JSON_QUERY = json[*]
    READ_FROM_FILE = NO
    REJECT_EMPTY_LISTS = YES
    FRAGMENTS -> JSONFragmenter_2
    FRAGMENTS -> JSONFragmenter_6
JSONFragmenter_6
    EXPLODE_FORMAT = JSON
    EXTRACT_ATTR = No
    JSON_ATTR = _response_body
    JSON_QUERY = json[*]
    READ_FROM_FILE = NO
    REJECT_EMPTY_LISTS = YES
    FRAGMENTS -> TestFilter
    <REJECTED> -> Logger_3
TestFilter
    DEFAULT_VALUE = <UNFILTERED>
    TEST_LIST:
      "BOOL_OP,OR,COMPOSITE_TEST,""""""1 OR 2 OR 3"""""",TEST_CLAUSE,TEST @Value(json_index) = timezone
      TEST @Value(json_index) = sunset
      TEST @Value(json_index) = sunrise",@Value(json_index) = timezone
    @Value(json_index) = timezone -> TestFilter_2
TestFilter_2
    DEFAULT_VALUE = <UNFILTERED>
    TEST_LIST = "BOOL_OP,OR,COMPOSITE_TEST,""""""1"""""",TEST_CLAUSE,TEST @Value(json_index) = sunrise",sunrise,"BOOL_OP,OR,COMPOSITE_TEST,""""""1"""""",TEST_CLAUSE,TEST @Value(json_index) = sunset",sunset,"BOOL_OP,OR,COMPOSITE_TEST,""""""1"""""",TEST_CLAUSE,TEST @Value(json_index) = timezone",timezone
    sunrise -> AttributeManager_2
    sunset -> AttributeManager_3
    timezone -> AttributeManager_4
AttributeManager_2
    ATTR_TABLE = RENAME_SET_VALUE _response_body > sunrise
    -> FeatureJoiner [LEFT]
AttributeManager_3
    ATTR_TABLE = RENAME_SET_VALUE _response_body > sunset
    -> FeatureJoiner [RIGHT]
FeatureJoiner
    ATTR_CONFLICT_RES = Use Left
    GEOMETRY_HANDLING = Use Left
    JOIN_KEYS = json_type json_type AUTO
    JOIN_MODE = Full
    JOINED -> FeatureJoiner_2 [LEFT]
AttributeManager_4
    ATTR_TABLE = RENAME_SET_VALUE _response_body > Timezone
    -> FeatureJoiner_2 [RIGHT]
FeatureJoiner_2
    ATTR_CONFLICT_RES = Use Left
    GEOMETRY_HANDLING = Use Left
    JOIN_KEYS = json_type json_type AUTO
    JOIN_MODE = Full
    JOINED -> AttributeManager_5
AttributeManager_5
    ATTR_TABLE:
      REMOVE json_type
      REMOVE json_index
      SET_TO _creation_instance = 0
      SET_TO timenow = @DateTimeFormat(@DateTimeNow(),%Y-%m-%d)
    -> AttributeManager
    -> AttributeManager_6
AttributeManager_6
    ATTR_TABLE:
      REMOVE sunrise
      REMOVE sunset
      REMOVE _creation_instance
      REMOVE timenow
    -> Cloner
Cloner
    COPIES = 40
    COPYATT = _copynum
    COPY -> FeatureJoiner_4 [RIGHT]
AttributeManager
    ATTR_TABLE:
      SET_TO sunrise = @DateTimeFormat(@DateTimeParse(@sum(@Value(sunrise),@Value(Timezone)),%s),%H:%m)
      SET_TO sunset = @DateTimeFormat(@DateTimeParse(@sum(@Value(sunset),@Value(Timezone)),%s),%H:%m)
      SET_TO Timezone = @ceil(@Value(Timezone)/3600)h@abs(@mult((@div(@abs(@Value(Timezone)),3600)-@ceil(@div(@abs(@Value(Timezone)),3600))),60))
      SET_TO Timezone = FME_CONDITIONAL:DEFAULT_VALUE'_FME_NO_OP_'BOOL_OP;OR;COMPOSITE_TEST;1;CASE_INSENSITIVE_TEST @Value(Timezone) CONTAINS h0'@ReplaceString(@Value(Timezone),h0,h,caseSensitive=TRUE)'FME_NUM_CONDITIONS2___
    -> FeatureJoiner_3 [LEFT]
FeatureJoiner_3
    ATTR_CONFLICT_RES = Use Left
    GEOMETRY_HANDLING = Use Left
    JOIN_KEYS = _creation_instance _creation_instance AUTO
    JOIN_MODE = Full
    JOINED -> AttributeManager_11
AttributeManager_11
    ATTR_TABLE:
      SET_TO Timezone = FME_CONDITIONAL:DEFAULT_VALUE'UTC +@Value(Timezone)'BOOL_OP;OR;COMPOSITE_TEST;1;CASE_INSENSITIVE_TEST @Value(Timezone) BEGINS_WITH -'UTC @Value(Timezone)'FME_NUM_CONDITIONS2___
      SET_TO join = 0
    -> FeatureJoiner_6 [LEFT]
Logger_3
    LOG_FEATURE = LOG_ONLY
    MAXCOORDS = 20
    MAXFEATS = 20
    MESSAGE = Feature is:
    SEVERITY = INFO
FeatureReader
    ATTRIBUTES = TOPO-OSM-WMS,"wms_service_name,wms_service_title,wms_service_abstract,wms_layer_name,wms_layer_title,wms_layer_abstract,wms_selected_layers,fme_geometry{0}"
    ATTR_ACCUM_MODE = Only Use Result
    COMBINE_GEOM = Use Result
    DATASET = http://ows.mundialis.de/services/service?
    FEATURETYPES = TOPO-OSM-WMS
    FORMAT = WMS
    INTERACT = Bounding Boxes Intersect
    OUTPUT_FEATURES_DISPLAY = Schema and Data Features
    WMS_MAP_FORMAT = image/png
    WMS_PIPE_DELIM = yes
    WMS_READER_META_ATTRIBUTES = fme_dataset fme_basename
    WMS_SPLIT_REQUEST = no
    WMS_SRS = EPSG:4326
    WMS_TRANSPARENT = no
    WMS_USE_SEARCH_ENVELOPE = NO
    WMS_WMS_LAYER_LIST = "{OpenStreetMap WMS}|{TOPO-OSM-WMS}"
    TOPO-OSM-WMS -> basemap_WR (writer PNGRASTER_1)
basemap_WR (writer PNGRASTER_1)
    attributes: wms_service_name char(254), wms_service_title char(254), wms_service_abstract char(254), wms_layer_name char(254), wms_layer_title char(254), wms_layer_abstract char(254), wms_selected_layers char(13), fme_geometry{0} char(200)
AttributeManager_106
    ATTR_TABLE:
      REMOVE _count00
      REMOVE _count2
      SET_TO rain = FME_CONDITIONAL:DEFAULT_VALUE'_FME_NO_OP_'BOOL_OP;OR;COMPOSITE_TEST;1;TEST rain ATTRIBUTE_IS_MISSING _FME_BLANK_STRING_'0'FME_NUM_CONDITIONS2___
      REMOVE _count99
      SET_TO snow = FME_CONDITIONAL:DEFAULT_VALUE'_FME_NO_OP_'BOOL_OP;OR;COMPOSITE_TEST;1;TEST snow ATTRIBUTE_IS_MISSING _FME_BLANK_STRING_'0'FME_NUM_CONDITIONS2___
    -> FeatureJoiner_4 [LEFT]
FeatureJoiner_4
    ATTR_CONFLICT_RES = Use Left
    GEOMETRY_HANDLING = Use Left
    JOIN_KEYS = _creation_instance _copynum AUTO
    JOIN_MODE = Inner
    JOINED -> AttributeManager_7
AttributeManager_7
    ATTR_TABLE:
      SET_TO dt = @Evaluate(@sum(@Value(dt),@Value(Timezone)))
      SET_TO dt_txt = @DateTimeFormat(@DateTimeParse(@Value(dt),%s),%Y-%m-%d %H:00:00)
      SET_TO temp_fl = @Evaluate(@Value(temp_fl)-273.15)
      SET_TO wind_gust = @Evaluate(@Value(wind_gust)/3.6)
      SET_TO wind_speed = @Evaluate(@Value(wind_speed)/3.6)
      SET_TO temp = @Evaluate(@Value(temp)-273.15)
      SET_TO temp_max = @Evaluate(@Value(temp_max)-273.15)
      SET_TO temp_min = @Evaluate(@Value(temp_min)-273.15)
      SET_TO rain = @Evaluate(@Value(rain)/3)
      SET_TO snow = @Evaluate(@Value(snow)/3)
      SET_TO wind_dir_txt = FME_CONDITIONAL:DEFAULT_VALUE'NNW'BOOL_OP;OR;COMPOSITE_TEST;1 OR 2;NUM_TEST @Value(wind_dir) < 11.25;TEST @Value(wind_dir) >= 348.75'N'BOOL_OP;AND;COMPOSITE_TEST;1 AND 2;NUM_TEST @Value(wind_dir) < 33.75;TEST @Value(wind_dir) >= 11.25'NNE'BOOL_OP;AND;COMPOSITE_TEST;1 AND 2;NUM_TEST @Value(wind_dir) < 56.25;TEST @Value(wind_dir) >= 33.75'NE'BOOL_OP;AND;COMPOSITE_TEST;1 AND 2;NUM_TEST @Value(wind_dir) < 78.75;TEST @Value(wind_dir) >= 56.25'ENE'BOOL_OP;AND;COMPOSITE_TEST;1 AND 2;NUM_TEST @Value(wind_dir) < 101.25;TEST @Value(wind_dir) >= 78.75'E'BOOL_OP;AND;COMPOSITE_TEST;1 AND 2;NUM_TEST @Value(wind_dir) < 123.75;TEST @Value(wind_dir) >= 101.25'ESE'BOOL_OP;AND;COMPOSITE_TEST;1 AND 2;NUM_TEST @Value(wind_dir) < 146.25;TEST @Value(wind_dir) >= 123.75'SE'BOOL_OP;AND;COMPOSITE_TEST;1 AND 2;NUM_TEST @Value(wind_dir) < 168.75;TEST @Value(wind_dir) >= 146.25'SSE'BOOL_OP;AND;COMPOSITE_TEST;1 AND 2;NUM_TEST @Value(wind_dir) < 191.25;TEST @Value(wind_dir) >= 168.75'S'BOOL_OP;AND;COMPOSITE_TEST;1 AND 2;NUM_TEST @Value(wind_dir) < 213.25;TEST @Value(wind_dir) >= 191.25'SSW'BOOL_OP;AND;COMPOSITE_TEST;1 AND 2;NUM_TEST @Value(wind_dir) < 236.25;TEST @Value(wind_dir) >= 213.75'SW'BOOL_OP;AND;COMPOSITE_TEST;1 AND 2;NUM_TEST @Value(wind_dir) < 258.75;TEST @Value(wind_dir) >= 236.25'WSW'BOOL_OP;AND;COMPOSITE_TEST;1 AND 2;NUM_TEST @Value(wind_dir) < 281.25;TEST @Value(wind_dir) >= 258.75'W'BOOL_OP;AND;COMPOSITE_TEST;1 AND 2;NUM_TEST @Value(wind_dir) < 303.75;TEST @Value(wind_dir) >= 281.25'W'BOOL_OP;AND;COMPOSITE_TEST;1 AND 2;NUM_TEST @Value(wind_dir) < 326.25;TEST @Value(wind_dir) >= 303.75'NW'FME_NUM_CONDITIONS16___
    -> prevision_t (writer CSV2_1)
    -> StatisticsCalculator
    -> Chart_Temperature
    -> Chart_Precipitation
    -> Chart_Wind
    -> Chart_Wind_2
    -> Chart_Pressure
    -> Chart_Pressure_2
    -> Chart_Pressure_3
    -> Chart_Pressure_4
    -> Chart_Pressure_5
Chart_Temperature: ChartGenerator
    AXES_FONT = Arial,9
    AXES_LW = 0.5
    BACKGROUND_COLOR = 1,1,1
    CHART_SETUP = XATT;dt;YATT;temp;EATT;;COLOR;1,0,0;LINE_STYLE;SOLID;LINEWEIGHT;1.0;FILL_AREA;YES;DISCRETE_X;NO;DISCRETE_Y;NO;POINT_STYLE;CIRCLE;FME_CONTROLLER_QUERY_FILE;transformers/dependencies/charter/Line.fme;FME_CONTROLLER_CHOICE;Line
    CHART_TITLE = "Temperature evolution "
    CHART_TYPE = Line
    DATA_SERIES = }Feels like [°C]{XATT;dt;YATT;temp_fl;EATT;;COLOR;0,0,0;LINE_STYLE;DOTTED;LINEWEIGHT;1.0;FILL_AREA;NO;DISCRETE_X;NO;DISCRETE_Y;NO;POINT_STYLE;CIRCLE;FME_CONTROLLER_QUERY_FILE;transformers/dependencies/charter/Line.fme;FME_CONTROLLER_CHOICE;Line}Temp_min{XATT;dt;YATT;temp;EATT;;COLOR;0,0,1;LINE_STYLE;DASH_DOT;LINEWEIGHT;1.0;FILL_AREA;NO;DISCRETE_X;NO;DISCRETE_Y;NO;POINT_STYLE;CIRCLE;FME_CONTROLLER_QUERY_FILE;transformers/dependencies/charter/Line.fme;FME_CONTROLLER_CHOICE;Line}Temp_max{XATT;dt;YATT;temp_max;EATT;;COLOR;0.333333,0,0;LINE_STYLE;DASH_DOT;LINEWEIGHT;1.0;FILL_AREA;NO;DISCRETE_X;NO;DISCRETE_Y;NO;POINT_STYLE;CIRCLE;FME_CONTROLLER_QUERY_FILE;transformers/dependencies/charter/Line.fme;FME_CONTROLLER_CHOICE;Line}Temperature [°C]{XATT;dt;YATT;temp;EATT;;COLOR;1,0,0;LINE_STYLE;SOLID;LINEWEIGHT;1.0;FILL_AREA;YES;DISCRETE_X;NO;DISCRETE_Y;NO;POINT_STYLE;CIRCLE;FME_CONTROLLER_QUERY_FILE;transformers/dependencies/charter/Line.fme;FME_CONTROLLER_CHOICE;Line
    DPI = 300
    INTERPRETATION = RGBA32
    LEGEND = A
    LEGEND_FONT = Arial,9
    LEGEND_OPTIONS = YES
    MULTI_DS = YES
    TICKS = T
    TICK_FONT = Arial,9
    TITLE_FONT = Arial,9
    X_INCH = 6
    X_LABEL_ANGLE = Horizontal (0)
    X_LOG = LIN
    Y_INCH = 4
    Y_LABEL = Temperature [°C]
    Y_LABEL_ANGLE = Horizontal (0)
    Y_LOG = LIN
    -> AttributeManager_13
AttributeManager_13
    ATTR_TABLE = SET_TO fme_basename = prevision_temp
    -> FeatureWriter [Output]
Chart_Precipitation: ChartGenerator
    AXES_FONT = Arial,9
    AXES_LW = 0.5
    BACKGROUND_COLOR = 1,1,1
    CHART_SETUP = XATT;dt;YATT;rain;EATT;;COLOR;0,1,0;LINE_STYLE;SOLID;LINEWEIGHT;1.0;FILL_AREA;NO;DISCRETE_X;YES;DISCRETE_Y;NO;POINT_STYLE;NONE;FME_CONTROLLER_QUERY_FILE;transformers/dependencies/charter/Line.fme;FME_CONTROLLER_CHOICE;Line
    CHART_TITLE = Prevision for precipitation
    CHART_TYPE = Line
    DATA_SERIES = }Rain Precipitation [mm/h]{XATT;dt;YATT;rain;EATT;;COLOR;0,0,1;LINE_STYLE;SOLID;LINEWEIGHT;1.0;FILL_AREA;YES;DISCRETE_X;YES;DISCRETE_Y;NO;POINT_STYLE;NONE;FME_CONTROLLER_QUERY_FILE;transformers/dependencies/charter/Line.fme;FME_CONTROLLER_CHOICE;Line}Snow Precipitation [mm/h]{XATT;dt;YATT;snow;EATT;;COLOR;0.482353,0.501961,0.545098;LINE_STYLE;SOLID;LINEWEIGHT;1.0;FILL_AREA;YES;DISCRETE_X;YES;DISCRETE_Y;NO;POINT_STYLE;NONE;FME_CONTROLLER_QUERY_FILE;transformers/dependencies/charter/Line.fme;FME_CONTROLLER_CHOICE;Line
    DPI = 300
    INTERPRETATION = RGBA32
    LEGEND = A
    LEGEND_FONT = Arial,9
    LEGEND_OPTIONS = YES
    MULTI_DS = YES
    TICKS = T
    TICK_FONT = Arial,10
    TITLE_FONT = Arial,9
    X_INCH = 6
    X_LABEL = time
    X_LABEL_ANGLE = Horizontal (0)
    X_LOG = LIN
    Y_INCH = 4
    Y_LABEL = Precipitation [mm/h]
    Y_LABEL_ANGLE = Horizontal (0)
    Y_LOG = LIN
    Y_MIN = 0
    -> AttributeManager_14
AttributeManager_14
    ATTR_TABLE = SET_TO fme_basename = prevision_precipitation
    -> FeatureWriter [Output]
Chart_Wind: ChartGenerator
    AXES_FONT = Arial,9
    AXES_LW = 0.5
    BACKGROUND_COLOR = 1,1,1
    CHART_SETUP = XATT;dt;YATT;rain;EATT;;COLOR;0,1,0;LINE_STYLE;SOLID;LINEWEIGHT;1.0;FILL_AREA;NO;DISCRETE_X;YES;DISCRETE_Y;NO;POINT_STYLE;NONE;FME_CONTROLLER_QUERY_FILE;transformers/dependencies/charter/Line.fme;FME_CONTROLLER_CHOICE;Line
    CHART_TITLE = Prevision for wind
    CHART_TYPE = Line
    DATA_SERIES = }Wind gust [km/h]{XATT;dt;YATT;wind_gust;EATT;;COLOR;0.333333,0,0;LINE_STYLE;DASH_DOT;LINEWEIGHT;1.0;FILL_AREA;YES;DISCRETE_X;YES;DISCRETE_Y;NO;POINT_STYLE;NONE;FME_CONTROLLER_QUERY_FILE;transformers/dependencies/charter/Line.fme;FME_CONTROLLER_CHOICE;Line}Wind speed [km/h]{XATT;dt;YATT;wind_speed;EATT;;COLOR;1,0.333333,0;LINE_STYLE;SOLID;LINEWEIGHT;1.0;FILL_AREA;YES;DISCRETE_X;YES;DISCRETE_Y;NO;POINT_STYLE;NONE;FME_CONTROLLER_QUERY_FILE;transformers/dependencies/charter/Line.fme;FME_CONTROLLER_CHOICE;Line
    DPI = 300
    INTERPRETATION = RGBA32
    LEGEND = A
    LEGEND_FONT = Arial,9
    LEGEND_OPTIONS = YES
    MULTI_DS = YES
    TICKS = T
    TICK_FONT = Arial,10
    TITLE_FONT = Arial,9
    XTICK_INTERVAL = 10
    X_INCH = 6
    X_LABEL = time
    X_LABEL_ANGLE = Horizontal (0)
    X_LOG = LIN
    Y_INCH = 4
    Y_LABEL = Speed [km/h]
    Y_LABEL_ANGLE = Horizontal (0)
    Y_LOG = LIN
    Y_MIN = 0
    -> AttributeManager_16
AttributeManager_16
    ATTR_TABLE = SET_TO fme_basename = prevision_wind
    -> FeatureWriter [Output]
Chart_Wind_2: ChartGenerator
    AXES_FONT = Arial,9
    AXES_LW = 0.5
    BACKGROUND_COLOR = 1,1,1
    CHART_SETUP = DATAATT;wind_speed;LABATT;wind_dir_txt;COLOR;0,0,0;BAR_ORIENTATION;V;BAR_STACKING;NO;BAR_WIDTH;1.0;FME_CONTROLLER_QUERY_FILE;transformers/dependencies/charter/Bar.fme;FME_CONTROLLER_CHOICE;Bar
    CHART_TITLE = Prevision for wind speed and direction
    CHART_TYPE = Bar
    DPI = 300
    INTERPRETATION = RGBA32
    LEGEND_OPTIONS = NO
    MULTI_DS = NO
    TICKS = T
    TICK_FONT = Arial,3
    TITLE_FONT = Arial,9
    X_INCH = 6
    X_LABEL = time
    X_LABEL_ANGLE = Horizontal (0)
    X_LOG = LIN
    Y_INCH = 4
    Y_LABEL = Speed [km/h]
    Y_LABEL_ANGLE = Horizontal (0)
    Y_LOG = LIN
    Y_MIN = 0
    -> AttributeManager_17
AttributeManager_17
    ATTR_TABLE = SET_TO fme_basename = prevision_wind_dir
    -> FeatureWriter [Output]
prevision_t (writer CSV2_1)
    attributes: dt string, dt_txt string, cloudiness string, wind_dir string, temp_fl string, pressure_gl string, wind_gust string, humidity string, pressure_sl string, pressure string, wind_speed string, temp string, temp_max string, temp_min string, visbility string, pop string, _creation_instance uint64, rain string, snow string, Timezone string, _copynum uint32, wind_dir_txt varchar(200)
Chart_Pressure: ChartGenerator
    AXES_FONT = Arial,9
    AXES_LW = 0.5
    BACKGROUND_COLOR = 1,1,1
    CHART_SETUP = XATT;dt;YATT;pressure_gl;EATT;;COLOR;0,1,0;LINE_STYLE;SOLID;LINEWEIGHT;2;FILL_AREA;NO;DISCRETE_X;YES;DISCRETE_Y;NO;POINT_STYLE;NONE;FME_CONTROLLER_QUERY_FILE;transformers/dependencies/charter/Line.fme;FME_CONTROLLER_CHOICE;Line
    CHART_TITLE = Prevision for pressure (ground level)
    CHART_TYPE = Line
    DPI = 300
    INTERPRETATION = RGBA32
    LEGEND = A
    LEGEND_FONT = Arial,10
    LEGEND_OPTIONS = YES
    MULTI_DS = NO
    TICKS = T
    TICK_FONT = Arial,10
    TITLE_FONT = Arial,9
    XTICK_INTERVAL = 10
    X_INCH = 6
    X_LABEL = time
    X_LABEL_ANGLE = Horizontal (0)
    X_LOG = LIN
    Y_INCH = 4
    Y_LABEL = Pressure [hPa]
    Y_LABEL_ANGLE = Horizontal (0)
    Y_LOG = LIN
    -> AttributeManager_18
AttributeManager_18
    ATTR_TABLE = SET_TO fme_basename = prevision_press_gl
    -> FeatureWriter [Output]
Chart_Pressure_2: ChartGenerator
    AXES_FONT = Arial,9
    AXES_LW = 0.5
    BACKGROUND_COLOR = 1,1,1
    CHART_SETUP = XATT;dt;YATT;pressure_sl;EATT;;COLOR;0,0.666667,0.498039;LINE_STYLE;SOLID;LINEWEIGHT;2;FILL_AREA;NO;DISCRETE_X;YES;DISCRETE_Y;NO;POINT_STYLE;NONE;FME_CONTROLLER_QUERY_FILE;transformers/dependencies/charter/Line.fme;FME_CONTROLLER_CHOICE;Line
    CHART_TITLE = Prevision for pressure (see level)
    CHART_TYPE = Line
    DPI = 300
    INTERPRETATION = RGBA32
    LEGEND = A
    LEGEND_FONT = Arial,9
    LEGEND_OPTIONS = YES
    MULTI_DS = NO
    TICKS = T
    TICK_FONT = Arial,10
    TITLE_FONT = Arial,9
    XTICK_INTERVAL = 10
    X_INCH = 6
    X_LABEL = time
    X_LABEL_ANGLE = Horizontal (0)
    X_LOG = LIN
    Y_INCH = 4
    Y_LABEL = Pressure [hPa]
    Y_LABEL_ANGLE = Horizontal (0)
    Y_LOG = LIN
    -> AttributeManager_19
AttributeManager_19
    ATTR_TABLE = SET_TO fme_basename = prevision_press_sl
    -> FeatureWriter [Output]
Chart_Pressure_3: ChartGenerator
    AXES_FONT = Arial,9
    AXES_LW = 0.5
    BACKGROUND_COLOR = 1,1,1
    CHART_SETUP = XATT;dt;YATT;cloudiness;EATT;;COLOR;0.341176,0.337255,0.388235;LINE_STYLE;SOLID;LINEWEIGHT;2;FILL_AREA;YES;DISCRETE_X;YES;DISCRETE_Y;NO;POINT_STYLE;NONE;FME_CONTROLLER_QUERY_FILE;transformers/dependencies/charter/Line.fme;FME_CONTROLLER_CHOICE;Line
    CHART_TITLE = Prevision for cloudiness
    CHART_TYPE = Line
    DPI = 300
    INTERPRETATION = RGBA32
    LEGEND = A
    LEGEND_FONT = Arial,9
    LEGEND_OPTIONS = YES
    MULTI_DS = NO
    TICKS = T
    TICK_FONT = Arial,10
    TITLE_FONT = Arial,9
    XTICK_INTERVAL = 10
    X_INCH = 6
    X_LABEL = time
    X_LABEL_ANGLE = Horizontal (0)
    X_LOG = LIN
    Y_INCH = 4
    Y_LABEL = Cloud coverage [%]
    Y_LABEL_ANGLE = Horizontal (0)
    Y_LOG = LIN
    -> AttributeManager_20
AttributeManager_20
    ATTR_TABLE = SET_TO fme_basename = prevision_cloudiness
    -> FeatureWriter [Output]
Chart_Pressure_4: ChartGenerator
    AXES_FONT = Arial,9
    AXES_LW = 0.5
    BACKGROUND_COLOR = 1,1,1
    CHART_SETUP = XATT;dt;YATT;humidity;EATT;;COLOR;0.341176,0.337255,0.388235;LINE_STYLE;SOLID;LINEWEIGHT;2;FILL_AREA;YES;DISCRETE_X;YES;DISCRETE_Y;NO;POINT_STYLE;NONE;FME_CONTROLLER_QUERY_FILE;transformers/dependencies/charter/Line.fme;FME_CONTROLLER_CHOICE;Line
    CHART_TITLE = "Prevision for humidity "
    CHART_TYPE = Line
    DPI = 300
    INTERPRETATION = RGBA32
    LEGEND = A
    LEGEND_FONT = Arial,9
    LEGEND_OPTIONS = YES
    MULTI_DS = NO
    TICKS = T
    TICK_FONT = Arial,10
    TITLE_FONT = Arial,9
    XTICK_INTERVAL = 10
    X_INCH = 6
    X_LABEL = time
    X_LABEL_ANGLE = Horizontal (0)
    X_LOG = LIN
    Y_INCH = 4
    Y_LABEL = Relative humidity [%]
    Y_LABEL_ANGLE = Horizontal (0)
    Y_LOG = LIN
    -> AttributeManager_21
AttributeManager_21
    ATTR_TABLE = SET_TO fme_basename = prevision_humidity
    -> FeatureWriter [Output]
FeatureWriter
    DATASET = $(DestDataset_CSV2)
    DATASET_ATTR = _dataset
    FEATURE_TYPE_LIST_ATTR = _feature_types
    FORMAT = PNGRASTER
    PNGRASTER_COORDINATE_SYSTEM_GRANULARITY = FEATURE
    TOTAL_FEATURES_WRITTEN_ATTR = _total_features_written
    SUMMARY -> AttributeManager_15
AttributeManager_15
    ATTR_TABLE:
      REMOVE _feature_types{}.count
      REMOVE _feature_types{}.name
      REMOVE _dataset
      REMOVE _total_features_written
      SET_TO join = 0
    -> FeatureJoiner_7 [RIGHT]
StatisticsCalculator
    CALCULATION_MODE = NUMERIC
    FEAT_STATS = dt,NUMERIC_MODE,MIN,MAX,,,,,,,,,,,
    COMPLETE -> TestFilter_3
TestFilter_3
    DEFAULT_VALUE = <UNFILTERED>
    TEST_LIST = "BOOL_OP,OR,COMPOSITE_TEST,""""""1"""""",TEST_CLAUSE,TEST @Value(dt) = @Value(dt.max)",@Value(dt) = @Value(dt.max),"BOOL_OP,OR,COMPOSITE_TEST,""""""1"""""",TEST_CLAUSE,TEST @Value(dt) = @Value(dt.min)",@Value(dt) = @Value(dt.min)
    @Value(dt) = @Value(dt.max) -> AttributeManager_9
    @Value(dt) = @Value(dt.min) -> AttributeManager_10
AttributeManager_9
    ATTR_TABLE:
      REMOVE dt
      RENAME_SET_VALUE dt_txt > dt_txt_max
      REMOVE cloudiness
      REMOVE wind_dir
      REMOVE temp_fl
      REMOVE pressure_gl
      REMOVE wind_gust
      REMOVE humidity
      REMOVE pressure_sl
      REMOVE pressure
      REMOVE wind_speed
      REMOVE temp
      REMOVE temp_max
      REMOVE temp_min
      REMOVE visbility
      REMOVE pop
      REMOVE _creation_instance
      REMOVE rain
      REMOVE snow
      REMOVE Timezone
      REMOVE _copynum
      REMOVE dt.min
    -> FeatureJoiner_5 [LEFT]
AttributeManager_10
    ATTR_TABLE:
      REMOVE dt
      RENAME_SET_VALUE dt_txt > dt_txt_min
      REMOVE cloudiness
      REMOVE wind_dir
      REMOVE temp_fl
      REMOVE pressure_gl
      REMOVE wind_gust
      REMOVE humidity
      REMOVE pressure_sl
      REMOVE pressure
      REMOVE wind_speed
      REMOVE temp
      REMOVE temp_max
      REMOVE temp_min
      REMOVE visbility
      REMOVE pop
      REMOVE _creation_instance
      REMOVE rain
      REMOVE snow
      REMOVE Timezone
      REMOVE _copynum
      REMOVE dt.min
    -> FeatureJoiner_5 [RIGHT]
FeatureJoiner_5
    ATTR_CONFLICT_RES = Use Left
    GEOMETRY_HANDLING = Use Left
    JOIN_KEYS = dt.max dt.max AUTO
    JOIN_MODE = Full
    JOINED -> AttributeManager_12
AttributeManager_12
    ATTR_TABLE:
      REMOVE dt.max
      SET_TO join = 0
    -> FeatureJoiner_6 [RIGHT]
FeatureJoiner_6
    ATTR_CONFLICT_RES = Use Left
    GEOMETRY_HANDLING = Use Left
    JOIN_KEYS = join join AUTO
    JOIN_MODE = Full
    JOINED -> FeatureJoiner_7 [LEFT]
FeatureJoiner_7
    ATTR_CONFLICT_RES = Use Left
    GEOMETRY_HANDLING = Use Left
    JOIN_KEYS = join join AUTO
    JOIN_MODE = Inner
    JOINED -> PythonCaller
PythonCaller
    PYTHONSOURCE:
      # -*- coding: utf-8 -*-
      #-------------------------------------------------------------------------------
      # Name:        Weather_report
      # Purpose:
      #
      # Author:      a.bugnard
      #
      # Created:     01.07.2022
      # Copyright:   (c) INSER SA, 2022 / ab

      #-------------------------------------------------------------------------------

      import fme
      import fmeobjects
      import shutil
      import zipfile
      import reportlab

      from reportlab.pdfgen import canvas
      from reportlab.pdfbase import pdfmetrics
      from reportlab.pdfbase.ttfonts import TTFont
      from reportlab.lib.utils import ImageReader
      import os, datetime, sys, traceback


      def main(feature):

          pdfmetrics.registerFont(TTFont('Vera', 'Vera.ttf'))
          pdfmetrics.registerFont(TTFont('VeraBd', 'VeraBd.ttf'))
          pdfmetrics.registerFont(TTFont('VeraIt', 'VeraIt.ttf'))
          pdfmetrics.registerFont(TTFont('VeraBI', 'VeraBI.ttf'))


          STR_TITLE = 'Weather & Air Pollution Report'
          STR_SUBTITLE1 = 'Location: ' + str(round(feature.getAttribute('_inside_y'), 4)) + ' N, ' + str(round(feature.getAttribute('_inside_x'), 4)) + ' E'
          STR_SUBTITLE2 = 'From ' + feature.getAttribute('dt_txt_min') + ' to ' + feature.getAttribute('dt_txt_max') + " (" + feature.getAttribute('Timezone') + ")"
          STR_SUBTITLE3 = 'Sunrise: ' + feature.getAttribute('sunrise') + '                                Sunset: ' + feature.getAttribute('sunset')
          PAGE = ['Page 1 of 6', 'Page 2 of 6', 'Page 3 of 6', 'Page 4 of 6', 'Page 5 of 6', 'Page 6 of 6', ]
          x1_start = 40
          y1_start = -20
          x2_start = 40
          y2_start = -370
          print(FME_MacroValues['DestDataset_CSV2'])
          can = canvas.Canvas(FME_MacroValues['DestDataset_CSV2']+"//Weather_report_" + FME_MacroValues['ISO3'] + ".pdf")
          can.setFont('VeraBd', 20)
          can.drawString(120, 800, "Weather & Air Pollution Report")
          can.drawImage('EXEL_FILES//deco1.png', 40, 775, width=500, preserveAspectRatio=True, mask='auto')
          can.drawImage('EXEL_FILES//deco2.png', 40, 20, width=500, preserveAspectRatio=True, mask='auto')
          can.drawImage('EXEL_FILES//deco3.png', 40, 770, width=50, preserveAspectRatio=True, mask='auto')
          can.drawImage('EXEL_FILES//deco4.png', 250, 770, width=50, preserveAspectRatio=True, mask='auto')
          can.drawImage(FME_MacroValues['DestDataset_PNGRASTER'] + "\\basemap_WR.png" , 190, 400, width=180, preserveAspectRatio=True, mask='auto')

          can.setFont('VeraIt', 12)
          can.drawString(110, 770, STR_SUBTITLE2)
          can.drawString(120, 750, STR_SUBTITLE3)
          can.drawString(200, 730, STR_SUBTITLE1)


          can.setFont('VeraBd', 13)
          can.drawString(40, 470, 'Table of contents')
          can.setFont('VeraBI', 12)
          can.drawString(40, 450, 'Weather')
          can.drawString(40, 340, 'Pollution')
          can.setFont('Vera', 11)
          can.drawString(45, 435,
                         'Temperature ........................................................................................................')
          can.drawString(45, 420,
                         'Precipitation .........................................................................................................')
          can.drawString(45, 405,
                         'Wind .....................................................................................................................')
          can.drawString(45, 390,
                         'Pressure ..............................................................................................................')
          can.drawString(45, 375,
                         'Humidity .............................................................................................................')
          can.drawString(45, 360,
                         'Cloudiness ...........................................................................................................')
          can.drawString(45, 325,
                         'NO2, NO, NH3, SO2, PM2.5, PM10 ......................................................................')
          can.drawString(45, 310,
                         'Ozone (O3) .........................................................................................................')
          can.drawString(45, 295,
                         'Carbon monoxyde (CO) ......................................................................................')
          can.drawString(495, 435, 'Page 2')
          can.drawString(495, 420, 'Page 2')
          can.drawString(495, 405, 'Page 3')
          can.drawString(495, 390, 'Page 4')
          can.drawString(495, 375, 'Page 4')
          can.drawString(495, 360, 'Page 5')
          can.drawString(495, 325, 'Page 5')
          can.drawString(495, 310, 'Page 6')
          can.drawString(495, 295, 'Page 6')

          can.setFont('VeraIt', 6)
          can.drawString(40, 120 + 40,
                         'The presented data come the OpenWeather API, that use its own numerical weather prediction (NWP) model, which uses several data sources:')
          can.drawString(45, 110 + 40, '-- Global NWP models:')
          can.drawString(53, 102 + 40, '- NOAA GFS 0.25 and 0.5 grid sizes (7 x7 and 14 x14 [km])')
          can.drawString(53, 95 + 40, '- NOAA CFS')
          can.drawString(53, 88 + 40, '- ECMWF ERA')
          can.drawString(45, 78 + 40, '-- Weather stations:')
          can.drawString(53, 70 + 40, '- METAR stations')
          can.drawString(53, 63 + 40, '- Users’ stations')
          can.drawString(53, 56 + 40, '- Companies’ stations')
          can.drawString(45, 46 + 40, '-- Weather radar data:')
          can.drawString(53, 38 + 40, '- Satellite data')
          can.drawString(40, 28 + 40,
                         'OpenWeather download and save data from these sources. Then it is processed by its in-house set of algorithms, to improve its quality and accuracy.')
          can.drawString(40, 20 + 40,
                         'This data processing is being done in real time, to provide the latest nowcasts and forecasts.')
          print(FME_MacroValues['DestDataset_CSV2']+"//Weather_report_" + FME_MacroValues['ISO3'] + ".pdf")


          can.showPage()
          #page2
          #------------------------------------------------------------------------------------------


          can.setFont('VeraBd', 13)
          can.drawString(20, 800, STR_TITLE)
          can.drawImage('EXEL_FILES//deco1.png', 20, 780, width=500, preserveAspectRatio=True, mask='auto')

          can.setFont('VeraBI', 10)
          can.drawString(20, 780, STR_SUBTITLE1)
          can.drawString(20, 765, STR_SUBTITLE2)
          can.setFont('VeraIt', 8)
          can.drawString(480, 20, PAGE[1])

          can.drawImage(FME_MacroValues['DestDataset_CSV2']+ '\prevision_temp.png', x1_start, y1_start, width=440, preserveAspectRatio=True, mask='auto')
          can.drawImage(FME_MacroValues['DestDataset_CSV2']+ '\prevision_precipitation.png', x2_start, y2_start, width=440, preserveAspectRatio=True, mask='auto')
          #page3
          #------------------------------------------------------------------------------------------
          can.showPage()

          can.setFont('VeraBd', 13)
          can.drawString(20, 800, STR_TITLE)
          can.drawImage('EXEL_FILES//deco1.png', 20, 780, width=500, preserveAspectRatio=True, mask='auto')

          can.setFont('VeraBI', 10)
          can.drawString(20, 780, STR_SUBTITLE1)
          can.drawString(20, 765, STR_SUBTITLE2)
          can.setFont('VeraIt', 8)
          can.drawString(480, 20, PAGE[2])

          can.drawImage(FME_MacroValues['DestDataset_CSV2']+ '\prevision_wind.png', x1_start, y1_start, width=440, preserveAspectRatio=True, mask='auto')
          can.drawImage(FME_MacroValues['DestDataset_CSV2']+ '\prevision_wind_dir.png', x2_start, y2_start, width=440, preserveAspectRatio=True, mask='auto')

          #page4
          #------------------------------------------------------------------------------------------
          can.showPage()

          can.setFont('VeraBd', 13)
          can.drawString(20, 800, STR_TITLE)
          can.drawImage('EXEL_FILES//deco1.png', 20, 780, width=500, preserveAspectRatio=True, mask='auto')

          can.setFont('VeraBI', 10)
          can.drawString(20, 780, STR_SUBTITLE1)
          can.drawString(20, 765, STR_SUBTITLE2)
          can.setFont('VeraIt', 8)
          can.drawString(480, 20, PAGE[3])

          can.drawImage(FME_MacroValues['DestDataset_CSV2']+ '\prevision_press_gl.png', x1_start, y1_start, width=440, preserveAspectRatio=True, mask='auto')
          can.drawImage(FME_MacroValues['DestDataset_CSV2']+ '\prevision_press_sl.png', x2_start, y2_start, width=440, preserveAspectRatio=True, mask='auto')


          #page5
          #------------------------------------------------------------------------------------------
          can.showPage()

          can.setFont('VeraBd', 13)
          can.drawString(20, 800, STR_TITLE)
          can.drawImage('EXEL_FILES//deco1.png', 20, 780, width=500, preserveAspectRatio=True, mask='auto')

          can.setFont('VeraBI', 10)
          can.drawString(20, 780, STR_SUBTITLE1)
          can.drawString(20, 765, STR_SUBTITLE2)
          can.setFont('VeraIt', 8)
          can.drawString(480, 20, PAGE[4])

          can.drawImage(FME_MacroValues['DestDataset_CSV2']+ '\prevision_humidity.png', x1_start, y1_start, width=440, preserveAspectRatio=True, mask='auto')
          can.drawImage(FME_MacroValues['DestDataset_CSV2']+ '\prevision_cloudiness.png', x2_start, y2_start, width=440, preserveAspectRatio=True, mask='auto')

          return can

      def processFeature(feature):
          can = main(feature)
          can.showPage()

          can.save()
          print("The end")
    PYTHONSYMBOL = processFeature
Chart_Pressure_5: ChartGenerator
    AXES_FONT = Arial,9
    AXES_LW = 0.5
    BACKGROUND_COLOR = 1,1,1
    CHART_SETUP = DATAATT;cloudiness;LABATT;pop;COLOR;0,1,0;BAR_ORIENTATION;V;BAR_STACKING;NO;BAR_WIDTH;1.0;FME_CONTROLLER_QUERY_FILE;transformers/dependencies/charter/Bar.fme;FME_CONTROLLER_CHOICE;Bar
    CHART_TITLE = "Prevision for humidity "
    CHART_TYPE = Bar
    DPI = 300
    INTERPRETATION = RGBA32
    LEGEND = A
    LEGEND_FONT = Arial,9
    LEGEND_OPTIONS = YES
    MULTI_DS = NO
    TICKS = T
    TICK_FONT = Arial,5
    TITLE_FONT = Arial,9
    X_INCH = 6
    X_LABEL = time
    X_LABEL_ANGLE = Horizontal (0)
    X_LOG = LIN
    Y_INCH = 4
    Y_LABEL = Relative humidity [%]
    Y_LABEL_ANGLE = Horizontal (0)
    Y_LOG = LIN
    -> AttributeManager_22
AttributeManager_22
    ATTR_TABLE = SET_TO fme_basename = prevision_humidity

Bookmark: Table Weather
JSONFragmenter_2
    EXPLODE_FORMAT = JSON
    EXTRACT_ATTR = No
    JSON_ATTR = _response_body
    JSON_QUERY = json[*]
    READ_FROM_FILE = NO
    REJECT_EMPTY_LISTS = YES
    FRAGMENTS -> JSONFragmenter_3
    <REJECTED> -> Logger
JSONFragmenter_3
    EXPLODE_FORMAT = JSON
    EXTRACT_ATTR = No
    JSON_ATTR = _response_body
    JSON_QUERY = json[*]
    READ_FROM_FILE = NO
    REJECT_EMPTY_LISTS = YES
    FRAGMENTS -> JSONFragmenter_4
    FRAGMENTS -> TestFilter_18
    FRAGMENTS -> TestFilter_21
    <REJECTED> -> Logger_2
JSONFragmenter_4
    EXPLODE_FORMAT = JSON
    EXTRACT_ATTR = No
    JSON_ATTR = _response_body
    JSON_QUERY = json[*]
    READ_FROM_FILE = NO
    REJECT_EMPTY_LISTS = YES
    FRAGMENTS -> JSONFragmenter_5
    <REJECTED> -> TestFilter_16
JSONFragmenter_5
    EXPLODE_FORMAT = JSON
    EXTRACT_ATTR = No
    JSON_ATTR = _response_body
    JSON_QUERY = json[*]
    READ_FROM_FILE = NO
    REJECT_EMPTY_LISTS = YES
    <REJECTED> -> TestFilter_17
TestFilter_17
    DEFAULT_VALUE = <UNFILTERED>
    TEST_LIST = "BOOL_OP,OR,COMPOSITE_TEST,""""""1"""""",TEST_CLAUSE,TEST @Value(json_index) = 3h",rain,"BOOL_OP,OR,COMPOSITE_TEST,""""""1"""""",TEST_CLAUSE,TEST @Value(json_index) = all",cloudiness,"BOOL_OP,OR,COMPOSITE_TEST,""""""1"""""",TEST_CLAUSE,TEST @Value(json_index) = deg",wind_dir,"BOOL_OP,OR,COMPOSITE_TEST,""""""1"""""",TEST_CLAUSE,TEST @Value(json_index) = feels_like",temp_fl,"BOOL_OP,OR,COMPOSITE_TEST,""""""1"""""",TEST_CLAUSE,TEST @Value(json_index) = grnd_level",pressure_gl,"BOOL_OP,OR,COMPOSITE_TEST,""""""1"""""",TEST_CLAUSE,TEST @Value(json_index) = gust",wind_gust,"BOOL_OP,OR,COMPOSITE_TEST,""""""1"""""",TEST_CLAUSE,TEST @Value(json_index) = humidity",humidity,"BOOL_OP,OR,COMPOSITE_TEST,""""""1"""""",TEST_CLAUSE,TEST @Value(json_index) = sea_level",pressure_sl,"BOOL_OP,OR,COMPOSITE_TEST,""""""1"""""",TEST_CLAUSE,TEST @Value(json_index) = pressure",pressure,"BOOL_OP,OR,COMPOSITE_TEST,""""""1"""""",TEST_CLAUSE,TEST @Value(json_index) = speed",wind_speed,"BOOL_OP,OR,COMPOSITE_TEST,""""""1"""""",TEST_CLAUSE,TEST @Value(json_index) = temp",temp,"BOOL_OP,OR,COMPOSITE_TEST,""""""1"""""",TEST_CLAUSE,TEST @Value(json_index) = temp_max",temp_max,"BOOL_OP,OR,COMPOSITE_TEST,""""""1"""""",TEST_CLAUSE,TEST @Value(json_index) = temp_min",temp_min,"BOOL_OP,OR,COMPOSITE_TEST,""""""1"""""",TEST_CLAUSE,TEST @Value(json_index) = 3h_s",snow
    rain -> Counter_7
    cloudiness -> Counter_8
    wind_dir -> Counter_9
    temp_fl -> Counter_13
    pressure_gl -> Counter_14
    wind_gust -> Counter_15
    humidity -> Counter_16
    pressure_sl -> Counter_17
    pressure -> Counter_18
    wind_speed -> Counter_19
    temp -> Counter_20
    temp_max -> Counter_21
    temp_min -> Counter_22
    snow -> Counter_27
Counter_8
    CNT_ATTR = _count2
    SCOPE = Local
    START = 0
    -> AttributeManager_88
AttributeManager_88
    ATTR_TABLE:
      RENAME_SET_VALUE _response_body > cloudiness
      REMOVE json_type
      REMOVE json_index
      REMOVE fme_rejection_code
    USER_EXPOSED_ATTRIBUTES = _count2
    -> FeatureJoiner_29 [LEFT]
Counter_9
    CNT_ATTR = _count3
    SCOPE = Local
    START = 0
    -> AttributeManager_89
AttributeManager_89
    ATTR_TABLE:
      RENAME_SET_VALUE _response_body > wind_dir
      REMOVE json_type
      REMOVE json_index
      REMOVE fme_rejection_code
    USER_EXPOSED_ATTRIBUTES = _count3
    -> FeatureJoiner_29 [RIGHT]
FeatureJoiner_29
    ATTR_CONFLICT_RES = Use Left
    GEOMETRY_HANDLING = Use Left
    JOIN_KEYS = _count2 _count3 AUTO
    JOIN_MODE = Left
    JOINED -> FeatureJoiner_30 [LEFT]
Counter_13
    CNT_ATTR = _count4
    SCOPE = Local
    START = 0
    -> AttributeManager_94
AttributeManager_94
    ATTR_TABLE:
      RENAME_SET_VALUE _response_body > temp_fl
      REMOVE json_type
      REMOVE json_index
      REMOVE fme_rejection_code
    USER_EXPOSED_ATTRIBUTES = _count4
    -> FeatureJoiner_30 [RIGHT]
FeatureJoiner_30
    ATTR_CONFLICT_RES = Use Left
    GEOMETRY_HANDLING = Use Left
    JOIN_KEYS = _count2 _count4 AUTO
    JOIN_MODE = Left
    JOINED -> FeatureJoiner_33 [LEFT]
Counter_14
    CNT_ATTR = _count5
    SCOPE = Local
    START = 0
    -> AttributeManager_95
AttributeManager_95
    ATTR_TABLE:
      RENAME_SET_VALUE _response_body > pressure_gl
      REMOVE json_type
      REMOVE json_index
      REMOVE fme_rejection_code
    USER_EXPOSED_ATTRIBUTES = _count5
    -> FeatureJoiner_33 [RIGHT]
FeatureJoiner_33
    ATTR_CONFLICT_RES = Use Left
    GEOMETRY_HANDLING = Use Left
    JOIN_KEYS = _count4 _count5 AUTO
    JOIN_MODE = Left
    JOINED -> FeatureJoiner_34 [LEFT]
Counter_15
    CNT_ATTR = _count6
    SCOPE = Local
    START = 0
    -> AttributeManager_96
AttributeManager_96
    ATTR_TABLE:
      RENAME_SET_VALUE _response_body > wind_gust
      REMOVE json_type
      REMOVE json_index
      REMOVE fme_rejection_code
    USER_EXPOSED_ATTRIBUTES = _count5
    -> FeatureJoiner_34 [RIGHT]
FeatureJoiner_34
    ATTR_CONFLICT_RES = Use Left
    GEOMETRY_HANDLING = Use Left
    JOIN_KEYS = _count4 _count6 AUTO
    JOIN_MODE = Left
    JOINED -> FeatureJoiner_35 [LEFT]
Counter_16
    CNT_ATTR = _count7
    SCOPE = Local
    START = 0
    -> AttributeManager_97
AttributeManager_97
    ATTR_TABLE:
      RENAME_SET_VALUE _response_body > humidity
      REMOVE json_type
      REMOVE json_index
      REMOVE fme_rejection_code
    USER_EXPOSED_ATTRIBUTES = _count5
    -> FeatureJoiner_35 [RIGHT]
FeatureJoiner_35
    ATTR_CONFLICT_RES = Use Left
    GEOMETRY_HANDLING = Use Left
    JOIN_KEYS = _count4 _count7 AUTO
    JOIN_MODE = Left
    JOINED -> FeatureJoiner_36 [LEFT]
Counter_17
    CNT_ATTR = _count8
    SCOPE = Local
    START = 0
    -> AttributeManager_98
AttributeManager_98
    ATTR_TABLE:
      RENAME_SET_VALUE _response_body > pressure_sl
      REMOVE json_type
      REMOVE json_index
      REMOVE fme_rejection_code
    USER_EXPOSED_ATTRIBUTES = _count5
    -> FeatureJoiner_36 [RIGHT]
FeatureJoiner_36
    ATTR_CONFLICT_RES = Use Left
    GEOMETRY_HANDLING = Use Left
    JOIN_KEYS = _count4 _count8 AUTO
    JOIN_MODE = Left
    JOINED -> FeatureJoiner_37 [LEFT]
Counter_18
    CNT_ATTR = _count8
    SCOPE = Local
    START = 0
    -> AttributeManager_99
AttributeManager_99
    ATTR_TABLE:
      RENAME_SET_VALUE _response_body > pressure
      REMOVE json_type
      REMOVE json_index
      REMOVE fme_rejection_code
    USER_EXPOSED_ATTRIBUTES = _count5
    -> FeatureJoiner_37 [RIGHT]
FeatureJoiner_37
    ATTR_CONFLICT_RES = Use Left
    GEOMETRY_HANDLING = Use Left
    JOIN_KEYS = _count4 _count8 AUTO
    JOIN_MODE = Left
    JOINED -> FeatureJoiner_38 [LEFT]
Counter_19
    CNT_ATTR = _count9
    SCOPE = Local
    START = 0
    -> AttributeManager_100
AttributeManager_100
    ATTR_TABLE:
      RENAME_SET_VALUE _response_body > wind_speed
      REMOVE json_type
      REMOVE json_index
      REMOVE fme_rejection_code
    USER_EXPOSED_ATTRIBUTES = _count5
    -> FeatureJoiner_38 [RIGHT]
FeatureJoiner_38
    ATTR_CONFLICT_RES = Use Left
    GEOMETRY_HANDLING = Use Left
    JOIN_KEYS = _count4 _count9 AUTO
    JOIN_MODE = Left
    JOINED -> FeatureJoiner_39 [LEFT]
Counter_20
    CNT_ATTR = _count10
    SCOPE = Local
    START = 0
    -> AttributeManager_101
AttributeManager_101
    ATTR_TABLE:
      RENAME_SET_VALUE _response_body > temp
      REMOVE json_type
      REMOVE json_index
      REMOVE fme_rejection_code
    USER_EXPOSED_ATTRIBUTES = _count5
    -> FeatureJoiner_39 [RIGHT]
FeatureJoiner_39
    ATTR_CONFLICT_RES = Use Left
    GEOMETRY_HANDLING = Use Left
    JOIN_KEYS = _count4 _count10 AUTO
    JOIN_MODE = Left
    JOINED -> FeatureJoiner_40 [LEFT]
Counter_21
    CNT_ATTR = _count11
    SCOPE = Local
    START = 0
    -> AttributeManager_102
AttributeManager_102
    ATTR_TABLE:
      RENAME_SET_VALUE _response_body > temp_max
      REMOVE json_type
      REMOVE json_index
      REMOVE fme_rejection_code
    USER_EXPOSED_ATTRIBUTES = _count5
    -> FeatureJoiner_40 [RIGHT]
FeatureJoiner_40
    ATTR_CONFLICT_RES = Use Left
    GEOMETRY_HANDLING = Use Left
    JOIN_KEYS = _count4 _count11 AUTO
    JOIN_MODE = Left
    JOINED -> FeatureJoiner_41 [LEFT]
Counter_22
    CNT_ATTR = _count12
    SCOPE = Local
    START = 0
    -> AttributeManager_103
AttributeManager_103
    ATTR_TABLE:
      RENAME_SET_VALUE _response_body > temp_min
      REMOVE json_type
      REMOVE json_index
      REMOVE fme_rejection_code
    USER_EXPOSED_ATTRIBUTES = _count5
    -> FeatureJoiner_41 [RIGHT]
FeatureJoiner_41
    ATTR_CONFLICT_RES = Use Left
    GEOMETRY_HANDLING = Use Left
    JOIN_KEYS = _count4 _count12 AUTO
    JOIN_MODE = Left
    JOINED -> AttributeManager_104
AttributeManager_104
    ATTR_TABLE:
      REMOVE _count3
      REMOVE _count4
      REMOVE _count5
      REMOVE _count6
      REMOVE _count7
      REMOVE _count8
      REMOVE _count9
      REMOVE _count10
      REMOVE _count11
      REMOVE _count12
    -> FeatureJoiner_42 [LEFT]
Counter_7
    CNT_ATTR = _count99
    DOMAIN = counter
    SCOPE = Global
    START = 0
    -> AttributeManager_87
AttributeManager_87
    ATTR_TABLE:
      RENAME_SET_VALUE _response_body > rain
      REMOVE json_type
      REMOVE json_index
      REMOVE fme_rejection_code
    USER_EXPOSED_ATTRIBUTES = _count1
    -> FeatureJoiner_44 [RIGHT]
Counter_27
    CNT_ATTR = _count9999
    SCOPE = Local
    START = 0
    -> AttributeManager_113
AttributeManager_113
    ATTR_TABLE:
      RENAME_SET_VALUE _response_body > snow
      REMOVE json_type
      REMOVE json_index
      REMOVE fme_rejection_code
    USER_EXPOSED_ATTRIBUTES = _count1
    -> FeatureJoiner_47 [RIGHT]
TestFilter_16
    DEFAULT_VALUE = <UNFILTERED>
    TEST_LIST = "BOOL_OP,OR,COMPOSITE_TEST,""""""1"""""",TEST_CLAUSE,TEST @Value(json_index) = dt",dt,"BOOL_OP,OR,COMPOSITE_TEST,""""""1"""""",TEST_CLAUSE,TEST @Value(json_index) = dt_txt",dt_txt,"BOOL_OP,OR,COMPOSITE_TEST,""""""1"""""",TEST_CLAUSE,TEST @Value(json_index) = visibility",visbility,"BOOL_OP,OR,COMPOSITE_TEST,""""""1"""""",TEST_CLAUSE,TEST @Value(json_index) = pop",pop
    dt -> Counter_4
    dt_txt -> Counter_5
    visbility -> Counter_6
    pop -> Counter_10
Counter_4
    CNT_ATTR = _count00
    SCOPE = Local
    START = 0
    -> AttributeManager_8
AttributeManager_8
    ATTR_TABLE:
      RENAME_SET_VALUE _response_body > dt
      REMOVE json_type
      REMOVE json_index
      REMOVE fme_rejection_code
    USER_EXPOSED_ATTRIBUTES = _count00
    -> FeatureJoiner_27 [LEFT]
Counter_5
    CNT_ATTR = _count01
    SCOPE = Local
    START = 0
    -> AttributeManager_85
AttributeManager_85
    ATTR_TABLE:
      RENAME_SET_VALUE _response_body > dt_txt
      REMOVE json_type
      REMOVE json_index
      REMOVE fme_rejection_code
    USER_EXPOSED_ATTRIBUTES = _count01
    -> FeatureJoiner_27 [RIGHT]
FeatureJoiner_27
    ATTR_CONFLICT_RES = Use Left
    GEOMETRY_HANDLING = Use Left
    JOIN_KEYS = _count00 _count01 AUTO
    JOIN_MODE = Left
    JOINED -> FeatureJoiner_28 [LEFT]
Counter_6
    CNT_ATTR = _count02
    SCOPE = Local
    START = 0
    -> AttributeManager_86
AttributeManager_86
    ATTR_TABLE:
      RENAME_SET_VALUE _response_body > visbility
      REMOVE json_type
      REMOVE json_index
      REMOVE fme_rejection_code
    USER_EXPOSED_ATTRIBUTES = _count02
    -> FeatureJoiner_28 [RIGHT]
FeatureJoiner_28
    ATTR_CONFLICT_RES = Use Left
    GEOMETRY_HANDLING = Use Left
    JOIN_KEYS = _count00 _count02 AUTO
    JOIN_MODE = Left
    JOINED -> FeatureJoiner_31 [LEFT]
Counter_10
    CNT_ATTR = _count03
    SCOPE = Local
    START = 0
    -> AttributeManager_90
AttributeManager_90
    ATTR_TABLE:
      RENAME_SET_VALUE _response_body > pop
      REMOVE json_type
      REMOVE json_index
      REMOVE fme_rejection_code
    USER_EXPOSED_ATTRIBUTES = _count03
    -> FeatureJoiner_31 [RIGHT]
FeatureJoiner_31
    ATTR_CONFLICT_RES = Use Left
    GEOMETRY_HANDLING = Use Left
    JOIN_KEYS = _count00 _count03 AUTO
    JOIN_MODE = Left
    JOINED -> AttributeManager_105
AttributeManager_105
    ATTR_TABLE:
      REMOVE _count01
      REMOVE _count02
      REMOVE _count03
    -> FeatureJoiner_42 [RIGHT]
FeatureJoiner_42
    ATTR_CONFLICT_RES = Use Left
    GEOMETRY_HANDLING = Use Left
    JOIN_KEYS = _count2 _count00 AUTO
    JOIN_MODE = Inner
    JOINED -> FeatureJoiner_45 [LEFT]
Logger_2
    LOG_FEATURE = LOG_ONLY
    MAXCOORDS = 20
    MAXFEATS = 20
    MESSAGE = Feature is:
    SEVERITY = INFO
TestFilter_18
    DEFAULT_VALUE = <UNFILTERED>
    TEST_LIST:
      "BOOL_OP,OR,COMPOSITE_TEST,""""""1 OR 2"""""",TEST_CLAUSE,TEST @Value(json_index) = dt
      TEST @Value(json_index) = rain",rain
    rain -> Counter_11
Counter_11
    CNT_ATTR = _count
    SCOPE = Local
    START = 0
    -> TestFilter_20
TestFilter_20
    DEFAULT_VALUE = <UNFILTERED>
    TEST_LIST = "BOOL_OP,OR,COMPOSITE_TEST,""""""1"""""",TEST_CLAUSE,TEST @Value(json_index) = rain",rain
    rain -> Counter_12
Counter_12
    CNT_ATTR = _countrain
    SCOPE = Local
    START = 0
    -> AttributeManager_92
AttributeManager_92
    ATTR_TABLE:
      REMOVE _response_body
      REMOVE json_type
      REMOVE json_index
      SET_TO rain = 1
      SET_TO indexrain = @Evaluate(@Value(_count)-@Value(_countrain)-1)
    -> AttributeManager_91
AttributeManager_91
    ATTR_TABLE:
      REMOVE _count
      RENAME_SET_VALUE rain > rainevent
      REMOVE _countrain
      SET_TO join = 0
    -> FeatureJoiner_32 [RIGHT]
    -> Counter_23
Counter_23
    CNT_ATTR = _count_000
    SCOPE = Local
    START = 0
    -> FeatureJoiner_44 [LEFT]
FeatureJoiner_44
    ATTR_CONFLICT_RES = Use Left
    GEOMETRY_HANDLING = Use Left
    JOIN_KEYS = _count_000 _count99 AUTO
    JOIN_MODE = Inner
    JOINED -> FeatureJoiner_43 [RIGHT]
TestFilter_21
    DEFAULT_VALUE = <UNFILTERED>
    TEST_LIST:
      "BOOL_OP,OR,COMPOSITE_TEST,""""""1 OR 2"""""",TEST_CLAUSE,TEST @Value(json_index) = dt
      TEST @Value(json_index) = snow",snow
    snow -> Counter_24
Counter_24
    CNT_ATTR = _count0000
    SCOPE = Local
    START = 0
    -> TestFilter_19
TestFilter_19
    DEFAULT_VALUE = <UNFILTERED>
    TEST_LIST = "BOOL_OP,OR,COMPOSITE_TEST,""""""1"""""",TEST_CLAUSE,TEST @Value(json_index) = snow",snow
    snow -> Counter_25
Counter_25
    CNT_ATTR = _countrain
    SCOPE = Local
    START = 0
    -> AttributeManager_109
AttributeManager_109
    ATTR_TABLE:
      REMOVE _response_body
      REMOVE json_type
      REMOVE json_index
      SET_TO snow = 1
      SET_TO indexsnow = @Evaluate(@Value(_count0000)-@Value(_countrain)-1)
    -> AttributeManager_110
AttributeManager_110
    ATTR_TABLE:
      REMOVE _countrain
      SET_TO join = 0
      RENAME_SET_VALUE snow > snowenvent
    USER_EXPOSED_ATTRIBUTES = snow
    -> FeatureJoiner_46 [RIGHT]
    -> Counter_26
Counter_26
    CNT_ATTR = _count_000
    SCOPE = Local
    START = 0
    -> FeatureJoiner_47 [LEFT]
FeatureJoiner_47
    ATTR_CONFLICT_RES = Use Left
    GEOMETRY_HANDLING = Use Left
    JOIN_KEYS = _count_000 _count9999 AUTO
    JOIN_MODE = Inner
    JOINED -> FeatureJoiner_48 [RIGHT]
Logger
    LOG_FEATURE = LOG_ONLY
    MAXCOORDS = 20
    MAXFEATS = 20
    MESSAGE = Feature is:
    SEVERITY = INFO
Creator_4
    GEOMTYPE = Geometry Object
    NUM = 40
    CREATED -> AttributeManager_111
AttributeManager_111
    ATTR_TABLE = SET_TO join = 0
    -> FeatureJoiner_46 [LEFT]
FeatureJoiner_46
    ATTR_CONFLICT_RES = Use Left
    GEOMETRY_HANDLING = Use Left
    JOIN_KEYS = _creation_instance indexsnow AUTO
    JOIN_MODE = Full
    JOINED -> AttributeManager_112
AttributeManager_112
    ATTR_TABLE:
      REMOVE join
      REMOVE indexsnow
      SET_TO snowenvent = FME_CONDITIONAL:DEFAULT_VALUE'_FME_NO_OP_'BOOL_OP;OR;COMPOSITE_TEST;1;TEST snowenvent ATTRIBUTE_VALUE_NULL _FME_BLANK_STRING_'0'FME_NUM_CONDITIONS2___
    -> FeatureJoiner_48 [LEFT]
FeatureJoiner_48
    ATTR_CONFLICT_RES = Use Left
    GEOMETRY_HANDLING = Use Left
    JOIN_KEYS = _creation_instance indexsnow AUTO
    JOIN_MODE = Full
    JOINED -> AttributeManager_114
AttributeManager_114
    ATTR_TABLE:
      REMOVE join
      REMOVE _count_000
      REMOVE _count1
      REMOVE _count0000
      REMOVE snowenvent
      REMOVE indexsnow
      SET_TO snow = FME_CONDITIONAL:DEFAULT_VALUE'_FME_NO_OP_'BOOL_OP;OR;COMPOSITE_TEST;1;TEST snow ATTRIBUTE_VALUE_NULL _FME_BLANK_STRING_'0'FME_NUM_CONDITIONS2___
      REMOVE _count111
      REMOVE _count9999
    USER_EXPOSED_ATTRIBUTES = rain,rainevent,indexrain,_count111
    -> FeatureJoiner_49 [RIGHT]
Creator_3
    GEOMTYPE = Geometry Object
    NUM = 40
    CREATED -> AttributeManager_93
AttributeManager_93
    ATTR_TABLE = SET_TO join = 0
    -> FeatureJoiner_32 [LEFT]
FeatureJoiner_32
    ATTR_CONFLICT_RES = Use Left
    GEOMETRY_HANDLING = Use Left
    JOIN_KEYS = _creation_instance indexrain AUTO
    JOIN_MODE = Full
    JOINED -> AttributeManager_107
AttributeManager_107
    ATTR_TABLE:
      REMOVE join
      REMOVE indexrain
      SET_TO rainevent = FME_CONDITIONAL:DEFAULT_VALUE'_FME_NO_OP_'BOOL_OP;OR;COMPOSITE_TEST;1;TEST rainevent ATTRIBUTE_VALUE_NULL _FME_BLANK_STRING_'0'FME_NUM_CONDITIONS2___
    -> FeatureJoiner_43 [LEFT]
FeatureJoiner_43
    ATTR_CONFLICT_RES = Use Left
    GEOMETRY_HANDLING = Use Left
    JOIN_KEYS = _creation_instance indexrain AUTO
    JOIN_MODE = Full
    JOINED -> AttributeManager_108
AttributeManager_108
    ATTR_TABLE:
      REMOVE rainevent
      REMOVE indexrain
      REMOVE join
      REMOVE _count_000
      SET_TO rain = FME_CONDITIONAL:DEFAULT_VALUE'_FME_NO_OP_'BOOL_OP;OR;COMPOSITE_TEST;1;TEST rain ATTRIBUTE_VALUE_NULL _FME_BLANK_STRING_'0'FME_NUM_CONDITIONS2___
      REMOVE _count1
    -> FeatureJoiner_45 [RIGHT]
FeatureJoiner_45
    ATTR_CONFLICT_RES = Use Left
    GEOMETRY_HANDLING = Use Left
    JOIN_KEYS = _count2 _creation_instance AUTO
    JOIN_MODE = Inner
    JOINED -> FeatureJoiner_49 [LEFT]
FeatureJoiner_49
    ATTR_CONFLICT_RES = Use Left
    GEOMETRY_HANDLING = Use Left
    JOIN_KEYS = _count2 _creation_instance AUTO
    JOIN_MODE = Inner
    JOINED -> AttributeManager_106
