FME workspace master.fmw

Parameters:
- BaseMap =
- EXCEL_FILES_SOURCE =
- Features_PDF =
- Light_mode =
- OSM_features =
- user_geom =

Readers:
- CSV2_1: CSV2 from C:\Users\alexandre\PycharmProjects\HGDR_geoFabrik\subregion3.csv

Creator
    GEOM = <?xml version="1.0" encoding="US_ASCII" standalone="no" ?><geometry><polygon><line><coord x="0" y="0"/><coord x="1" y="0"/><coord x="1" y="1"/><coord x="0" y="1"/><coord x="0" y="0"/></line></polygon></geometry>
    GEOMTYPE = Geometry Object
    NUM = 1
    CREATED -> WorkspaceRunner
    CREATED -> AttributeCreator
AttributeCreator
    ATTR_TABLE = SET_TO user_BB = $(user_geom)
    -> AttributeManager
AttributeManager
    ATTR_TABLE = SET_TO user_BB = @ReplaceString($(user_geom), ,;,caseSensitive=TRUE)
    -> AttributeSplitter
AttributeSplitter
    ATTR_NAME = user_BB
    DELIMITER = ;
    DROP_EMPTY_PARTS = No
    LIST_NAME = _min_max_BB
    TRIM_OPTION = Both
    -> AttributeManager_2
AttributeManager_2
    ATTR_TABLE:
      REMOVE user_BB
      SET_TO min_x = @Value(_min_max_BB{0})
      SET_TO min_y = @Value(_min_max_BB{1})
      SET_TO max_x = @Value(_min_max_BB{2})
      SET_TO max_y = @Value(_min_max_BB{3})
    -> Cloner
Cloner
    COPIES = 5
    COPYATT = _copynum
    COPY -> VertexCreator
VertexCreator
    MEASURE_TYPE = Continuous
    MODE_NAME = Replace with Point
    XVAL = FME_CONDITIONAL:DEFAULT_VALUE''BOOL_OP;OR;COMPOSITE_TEST;1;TEST @Value(_copynum) = 0'@Value(min_x)'BOOL_OP;OR;COMPOSITE_TEST;1;TEST @Value(_copynum) = 1'@Value(max_x)'BOOL_OP;OR;COMPOSITE_TEST;1;TEST @Value(_copynum) = 2'@Value(max_x)'BOOL_OP;OR;COMPOSITE_TEST;1;TEST @Value(_copynum) = 3'@Value(min_x)'BOOL_OP;OR;COMPOSITE_TEST;1;TEST @Value(_copynum) = 4'@Value(min_x)'FME_NUM_CONDITIONS6___
    YVAL = FME_CONDITIONAL:DEFAULT_VALUE''BOOL_OP;OR;COMPOSITE_TEST;1;TEST @Value(_copynum) = 0'@Value(max_y)'BOOL_OP;OR;COMPOSITE_TEST;1;TEST @Value(_copynum) = 1'@Value(max_y)'BOOL_OP;OR;COMPOSITE_TEST;1;TEST @Value(_copynum) = 2'@Value(min_y)'BOOL_OP;OR;COMPOSITE_TEST;1;TEST @Value(_copynum) = 3'@Value(min_y)'BOOL_OP;OR;COMPOSITE_TEST;1;TEST @Value(_copynum) = 4'@Value(max_y)'FME_NUM_CONDITIONS6___
    -> CoordinateSystemSetter
CoordinateSystemSetter
    COORDSYS = LL-WGS84
    -> LineBuilder
    -> TestFilter
LineBuilder
    ACCUM_INPUT_ATTRS = Use Attributes From One Feature
    REMOVE_DUPLICATES = No
    POLYGON -> AreaCalculator
AreaCalculator
    AREA_ATTR = _area
    AREA_TYPE = Plane Area
    MULT = 1
TestFilter
    DEFAULT_VALUE = <UNFILTERED>
    TEST_LIST:
      "BOOL_OP,OR,COMPOSITE_TEST,""""""1 OR 2"""""",TEST_CLAUSE,TEST @Value(_copynum) = 0
      TEST @Value(_copynum) = 1",len_lon,"BOOL_OP,OR,COMPOSITE_TEST,""""""1 OR 2"""""",TEST_CLAUSE,TEST @Value(_copynum) = 3
      TEST @Value(_copynum) = 4",len_lat
    len_lon -> LineBuilder_2
    len_lat -> LineBuilder_3
LineBuilder_2
    ACCUM_INPUT_ATTRS = Use Attributes From One Feature
    REMOVE_DUPLICATES = No
    LINE -> AttributeManager_4
AttributeManager_4
    ATTR_TABLE = SET_TO lat_lon = longitude
    -> LengthCalculator
LineBuilder_3
    ACCUM_INPUT_ATTRS = Use Attributes From One Feature
    REMOVE_DUPLICATES = No
    LINE -> AttributeManager_5
AttributeManager_5
    ATTR_TABLE = SET_TO lat_lon = latitude
    -> LengthCalculator
LengthCalculator
    DIM = 2
    LEN_ATTR = _length
    MULT = 1
    -> StatisticsCalculator
StatisticsCalculator
    CALCULATION_MODE = NUMERIC
    FEAT_STATS = _length,NUMERIC_MODE,,MAX,,,,,,,,,,,
    COMPLETE -> TestFilter_2
TestFilter_2
    DEFAULT_VALUE = <UNFILTERED>
    TEST_LIST = "BOOL_OP,OR,COMPOSITE_TEST,""""""1"""""",TEST_CLAUSE,TEST @Value(_length) = @Value(_length.max)",max_value
    max_value -> GeometryRemover
GeometryRemover
    -> Cloner_2
Cloner_2
    COPIES = 5
    COPYATT = _copynum
    COPY -> VertexCreator_2
VertexCreator_2
    MEASURE_TYPE = Continuous
    MODE_NAME = Replace with Point
    XVAL = FME_CONDITIONAL:DEFAULT_VALUE''BOOL_OP;AND;COMPOSITE_TEST;1 AND 2;TEST @Value(_copynum) = 0;TEST @Value(lat_lon) = latitude'@Value(min_x)'BOOL_OP;AND;COMPOSITE_TEST;1 AND 2;TEST @Value(_copynum) = 1;TEST @Value(lat_lon) = latitude'@Value(min_x)+@Value(_length.max)'BOOL_OP;AND;COMPOSITE_TEST;1 AND 2;TEST @Value(_copynum) = 2;TEST @Value(lat_lon) = latitude'@Value(min_x)+@Value(_length.max)'BOOL_OP;AND;COMPOSITE_TEST;1 AND 2;TEST @Value(_copynum) = 3;TEST @Value(lat_lon) = latitude'@Value(min_x)'BOOL_OP;AND;COMPOSITE_TEST;1 AND 2;TEST @Value(_copynum) = 4;TEST @Value(lat_lon) = latitude'@Value(min_x)'BOOL_OP;AND;COMPOSITE_TEST;1 AND 2;TEST @Value(_copynum) = 0;TEST @Value(lat_lon) = longitude'@Value(min_x)'BOOL_OP;AND;COMPOSITE_TEST;1 AND 2;TEST @Value(_copynum) = 1;TEST @Value(lat_lon) = longitude'@Value(max_x)'BOOL_OP;AND;COMPOSITE_TEST;1 AND 2;TEST @Value(_copynum) = 2;TEST @Value(lat_lon) = longitude'@Value(max_x)'BOOL_OP;AND;COMPOSITE_TEST;1 AND 2;TEST @Value(_copynum) = 3;TEST @Value(lat_lon) = longitude'@Value(min_x)'BOOL_OP;AND;COMPOSITE_TEST;1 AND 2;TEST @Value(_copynum) = 4;TEST @Value(lat_lon) = longitude'@Value(min_x)'FME_NUM_CONDITIONS11___
    YVAL = FME_CONDITIONAL:DEFAULT_VALUE'ERROR'BOOL_OP;AND;COMPOSITE_TEST;1 AND 2;TEST @Value(_copynum) = 0;TEST @Value(lat_lon) = latitude'@Value(max_y)'BOOL_OP;AND;COMPOSITE_TEST;1 AND 2;TEST @Value(_copynum) = 1;TEST @Value(lat_lon) = latitude'@Value(max_y)'BOOL_OP;AND;COMPOSITE_TEST;1 AND 2;TEST @Value(_copynum) = 2;TEST @Value(lat_lon) = latitude'@Value(min_y)'BOOL_OP;AND;COMPOSITE_TEST;1 AND 2;TEST @Value(_copynum) = 3;TEST @Value(lat_lon) = latitude'@Value(min_y)'BOOL_OP;AND;COMPOSITE_TEST;1 AND 2;TEST @Value(_copynum) = 4;TEST @Value(lat_lon) = latitude'@Value(max_y)'BOOL_OP;AND;COMPOSITE_TEST;1 AND 2;TEST @Value(_copynum) = 0;TEST @Value(lat_lon) = longitude'@Value(min_y)+@Value(_length.max)'BOOL_OP;AND;COMPOSITE_TEST;1 AND 2;TEST @Value(_copynum) = 1;TEST @Value(lat_lon) = longitude'@Value(min_y)+@Value(_length.max)'BOOL_OP;AND;COMPOSITE_TEST;1 AND 2;TEST @Value(_copynum) = 2;TEST @Value(lat_lon) = longitude'@Value(min_y)'BOOL_OP;AND;COMPOSITE_TEST;1 AND 2;TEST @Value(_copynum) = 3;TEST @Value(lat_lon) = longitude'@Value(min_y)'BOOL_OP;AND;COMPOSITE_TEST;1 AND 2;TEST @Value(_copynum) = 4;TEST @Value(lat_lon) = longitude'@Value(min_y)+@Value(_length.max)'FME_NUM_CONDITIONS11___
    -> LineBuilder_4
LineBuilder_4
    ACCUM_INPUT_ATTRS = Use Attributes From One Feature
    REMOVE_DUPLICATES = No
    POLYGON -> PointOnAreaOverlayer [AREA]
    POLYGON -> BoundsExtractor
BoundsExtractor
    XMAX = _xmax
    XMIN = _xmin
    YMAX = _ymax
    YMIN = _ymin
    -> Cloner_3
Cloner_3
    COPIES = 8
    COPYATT = _copynum
    COPY -> Cloner_4
Cloner_4
    COPIES = 8
    COPYATT = _copynum2
    COPY -> VertexCreator_3
VertexCreator_3
    MEASURE_TYPE = Continuous
    MODE_NAME = Replace with Point
    XVAL = @Value(_xmin)+((@Value(_xmax)-@Value(_xmin))/7)*@Value(_copynum2)
    YVAL = @Value(_ymin)+((@Value(_ymax)-@Value(_ymin))/7)*@Value(_copynum)
    -> PointOnAreaOverlayer [POINT]
PointOnAreaOverlayer
    ATTR_ACCUM_MODE = Merge Incoming
    ATTR_CONFLICT_RES = Use Original
    CANDIDATE_LIST_ATTRS_TO_INCLUDE_MODE = Selected Attributes
    DEAGGREGATE_INPUT = Yes
    OV_ATTR = _overlaps
    POLYS_FIRST = No
    POINT -> AttributeManager_7
    AREA -> CoordinateExtractor_2
    AREA -> FeatureJoiner_50 [RIGHT]
AttributeManager_7
    ATTR_TABLE:
      REMOVE min_x
      REMOVE min_y
      REMOVE max_x
      REMOVE max_y
      REMOVE _copynum
      REMOVE lat_lon
      REMOVE _length.max
      REMOVE _copynum2
      REMOVE _overlaps
    -> CoordinateExtractor
CoordinateExtractor
    IND = 0
    MODE = Specify Coordinate
    X_ATTR = _x
    Y_ATTR = _y
    -> Geocoder
Geocoder
    GEOCODING_SERVICE = OpenCage
    RETURN_JSON_RESPONSE = yes
    THREADS = 4
    TIMEOUT = 120
    VERIFY_HTTPS = yes
    -> StringReplacer_3
StringReplacer
    CASE = NO
    FIND_TEXT = \u00fc
    NO_MATCH = _FME_NO_OP_
    REGEXP = NO
    REPLACE_TEXT = ü
    SRC_ATTRS = _json_response
    -> StringSearcher
    -> StringSearcher_2
    -> StringSearcher_5
    -> StringSearcher_6
FeatureJoiner_4
    ATTR_CONFLICT_RES = Use Left
    GEOMETRY_HANDLING = Use Left
    JOIN_KEYS = _json_response _json_response AUTO
    JOIN_MODE = Inner
    JOINED -> FeatureJoiner_5 [LEFT]
FeatureJoiner_5
    ATTR_CONFLICT_RES = Use Left
    GEOMETRY_HANDLING = Use Left
    JOIN_KEYS = _json_response _json_response AUTO
    JOIN_MODE = Inner
    JOINED -> FeatureJoiner_3 [LEFT]
FeatureJoiner_3
    ATTR_CONFLICT_RES = Use Left
    GEOMETRY_HANDLING = Use Left
    JOIN_KEYS = _json_response _json_response AUTO
    JOIN_MODE = Inner
    JOINED -> AttributeManager_11
AttributeManager_11
    ATTR_TABLE:
      REMOVE _creation_instance
      REMOVE _min_max_BB{}
      REMOVE _length
      REMOVE _xmax
      REMOVE _xmin
      REMOVE _ymax
      REMOVE _ymin
      REMOVE _x
      REMOVE _y
      REMOVE _address
      REMOVE _latitude
      REMOVE _longitude
      REMOVE _json_response
      SET_TO state = FME_CONDITIONAL:DEFAULT_VALUE'_FME_NO_OP_'BOOL_OP;OR;COMPOSITE_TEST;1;TEST @Value(state) = Wallis'valais'BOOL_OP;OR;COMPOSITE_TEST;1;TEST @Value(state) = Luzern'lucerne'FME_NUM_CONDITIONS3___
      SET_TO join = 0
    -> DuplicateFilter_2
DuplicateFilter_2
    INPUT_ORDERED_CHOICE = No
    KEYATTR = country county region state
    UNIQUE -> FeatureReader_2 [INITIATOR]
FeatureReader_2
    ATTRIBUTES = CSV,"Country,Continent,Population,Size_MB,b_per_cap,area_km2,PopDens_cap_km2,ISO2,ISO3,IDH,OSMFR,subregion"
    ATTR_ACCUM_MODE = Merge Initiator and Result
    ATTR_CONFLICT_RES = Use Result
    ATTR_IGNORE_NULLS = No
    COMBINE_GEOM = Use Result
    CSV2_CASE_SENSITIVE_FIELD_NAMES = Yes
    CSV2_CHUNK_SIZE = 100000
    CSV2_DATA_START_LINE = 2
    CSV2_DATE_INPUT_FORMAT = FME
    CSV2_DELIMITER = auto
    CSV2_ENCODING = windows-1252
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = Yes
    CSV2_SCAN_ADDITIONAL_FIELDS = No
    CSV2_SCAN_MAX_ROWS = 10000
    CSV2_SCAN_TYPES = Yes
    CSV2_SKIP_DUPLICATE_DELIMITERS = No
    CSV2_STRING_TYPE_ATTRIBUTE_HANDLING = EXPLICIT_WIDTH
    CSV2_SUPPORTED_READER_ARCHIVE_EXTENSIONS = csv.gz,txt.gz
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_TYPE_ATTRIBUTE_HANDLING = STANDARD_TYPES
    CSV2_USE_CUSTOM_SCHEMA = NO
    DATASET = $(FME_MF_DIR_ENCODED)EXEL_FILES\quality_OSM.csv
    FORMAT = CSV2
    INTERACT = NONE
    OUTPUT_FEATURES_DISPLAY = Schema and Data Features
    CSV -> FuzzyStringComparer_2
FuzzyStringComparer_2
    DEST_ATTR = matchORnot
    STRING1 = @LowerCase(@Value(ISO2))
    STRING2 = @Value(country)
    -> TestFilter_5
TestFilter_5
    DEFAULT_VALUE = <UNFILTERED>
    TEST_LIST = "BOOL_OP,OR,COMPOSITE_TEST,""""""1"""""",TEST_CLAUSE,TEST @Value(matchORnot) > 0.95",passed
    passed -> TestFilter_6
TestFilter_6
    DEFAULT_VALUE = without_subregion
    TEST_LIST = "BOOL_OP,OR,COMPOSITE_TEST,""""""1"""""",TEST_CLAUSE,TEST @Value(subregion) = 1",with_subregion
    with_subregion -> TestFilter_10
    without_subregion -> AttributeManager_12
TestFilter_10
    DEFAULT_VALUE = direct_processing
    TEST_LIST:
      "BOOL_OP,OR,COMPOSITE_TEST,""""""1 OR 2 OR 3 OR 4 OR 5 OR 6"""""",TEST_CLAUSE,TEST @Value(ISO2) = EN
      TEST @Value(ISO2) = FR
      TEST @Value(ISO2) = ID
      TEST @Value(ISO2) = IN
      TEST @Value(ISO2) = IT
      TEST @Value(ISO2) = JP",relation_needed
    relation_needed -> FeatureReader_4 [INITIATOR]
    direct_processing -> FeatureReader_3 [INITIATOR]
FeatureReader_3
    ATTRIBUTES = CSV,State
    ATTR_ACCUM_MODE = Merge Initiator and Result
    ATTR_CONFLICT_RES = Use Result
    ATTR_IGNORE_NULLS = No
    COMBINE_GEOM = Use Result
    CSV2_CASE_SENSITIVE_FIELD_NAMES = Yes
    CSV2_CHUNK_SIZE = 100000
    CSV2_DATA_START_LINE = 2
    CSV2_DATE_INPUT_FORMAT = FME
    CSV2_DELIMITER = auto
    CSV2_ENCODING = windows-1252
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = Yes
    CSV2_SCAN_ADDITIONAL_FIELDS = No
    CSV2_SCAN_MAX_ROWS = 10000
    CSV2_SCAN_TYPES = Yes
    CSV2_SKIP_DUPLICATE_DELIMITERS = No
    CSV2_STRING_TYPE_ATTRIBUTE_HANDLING = EXPLICIT_WIDTH
    CSV2_SUPPORTED_READER_ARCHIVE_EXTENSIONS = csv.gz,txt.gz
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_TYPE_ATTRIBUTE_HANDLING = STANDARD_TYPES
    CSV2_USE_CUSTOM_SCHEMA = NO
    DATASET = $(FME_MF_DIR_ENCODED)EXEL_FILES\subregion_full.csv
    FORMAT = CSV2
    INTERACT = NONE
    OUTPUT_FEATURES_DISPLAY = Schema and Data Features
    CSV -> AttributeManager_10
AttributeManager_10
    ATTR_TABLE:
      RENAME_SET_VALUE State > stateANDcountry
      SET_TO join = 0
      SET_TO State = @Value(stateANDcountry)
    -> StringSearcher_3
StringSearcher_3
    CASE = no
    MATCHED_RESULT_ATTR = _first_match
    REGEXP = .{0,15}/
    STRING_TO_SEARCH = @Value(stateANDcountry)
    MATCHED -> StringReplacer_2
StringReplacer_2
    CASE = NO
    FIND_TEXT = @Value(_first_match)
    NO_MATCH = _FME_NO_OP_
    REGEXP = NO
    SRC_ATTRS = State
    -> AttributeManager_36
AttributeManager_36
    ATTR_TABLE:
      RENAME_SET_VALUE _first_match > Country_comp
      SET_TO Country_comp = @ReplaceString(@Value(Country_comp),/,,caseSensitive=TRUE)
    -> TestFilter_9
TestFilter_9
    DEFAULT_VALUE = <UNFILTERED>
    TEST_LIST = "BOOL_OP,OR,COMPOSITE_TEST,""""""1"""""",TEST_CLAUSE,TEST @LowerCase(@Value(Country)) = @Value(Country_comp)",@Value(Country) = @Value(country)
    @Value(Country) = @Value(country) -> AttributeManager_38
AttributeManager_38
    ATTR_TABLE = SET_TO state = FME_CONDITIONAL:DEFAULT_VALUE'_FME_NO_OP_'BOOL_OP;OR;COMPOSITE_TEST;1;TEST @Value(state) = Bavaria'Bayern'BOOL_OP;OR;COMPOSITE_TEST;1;TEST @Value(state) = North Rhine-Westphalia'nordrhein-westfalen'BOOL_OP;OR;COMPOSITE_TEST;1;TEST @Value(state) = Lower Saxony'Niedersachsen'FME_NUM_CONDITIONS4___
    -> FuzzyStringComparer
FuzzyStringComparer
    DEST_ATTR = matchORnot
    STRING1 = @LowerCase(@Value(state))
    STRING2 = @Value(State)
    -> TestFilter_3
TestFilter_3
    DEFAULT_VALUE = <UNFILTERED>
    TEST_LIST = "BOOL_OP,OR,COMPOSITE_TEST,""""""1"""""",TEST_CLAUSE,TEST @Value(matchORnot) > 0.71",passed
    passed -> AttributeManager_12
AttributeManager_12
    ATTR_TABLE:
      REMOVE matchORnot
      REMOVE join
      REMOVE State
      SET_TO url = FME_CONDITIONAL:DEFAULT_VALUE'@LowerCase(https://download.geofabrik.de/@Value(Continent)/@Value(Country)-latest.osm.pbf)'BOOL_OP;OR;COMPOSITE_TEST;1;TEST @Value(OSMFR) = 1'https://download.openstreetmap.fr/extracts/@Value(Continent)/@Value(stateANDcountry)-latest.osm.pbf'BOOL_OP;AND;COMPOSITE_TEST;1 AND 2;TEST @Value(OSMFR) = 0;TEST @Value(subregion) = 1'@LowerCase(https://download.geofabrik.de/@Value(Continent)/@Value(stateANDcountry)-latest.osm.pbf)'FME_NUM_CONDITIONS3___
    -> DuplicateFilter
FeatureReader_4
    ATTR_ACCUM_MODE = Merge Initiator and Result
    ATTR_CONFLICT_RES = Use Result
    ATTR_IGNORE_NULLS = No
    COMBINE_GEOM = Use Result
    CSV2_CASE_SENSITIVE_FIELD_NAMES = Yes
    CSV2_CHUNK_SIZE = 100000
    CSV2_DATA_START_LINE = 2
    CSV2_DATE_INPUT_FORMAT = FME
    CSV2_DELIMITER = auto
    CSV2_ENCODING = windows-1252
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = Yes
    CSV2_SCAN_ADDITIONAL_FIELDS = No
    CSV2_SCAN_MAX_ROWS = 10000
    CSV2_SCAN_TYPES = Yes
    CSV2_SKIP_DUPLICATE_DELIMITERS = No
    CSV2_STRING_TYPE_ATTRIBUTE_HANDLING = EXPLICIT_WIDTH
    CSV2_SUPPORTED_READER_ARCHIVE_EXTENSIONS = csv.gz,txt.gz
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_TYPE_ATTRIBUTE_HANDLING = STANDARD_TYPES
    CSV2_USE_CUSTOM_SCHEMA = NO
    DATASET = $(FME_MF_DIR_ENCODED)EXEL_FILES\relation_@Value(ISO2).csv
    FORMAT = CSV2
    INTERACT = NONE
    OUTPUT_FEATURES_DISPLAY = Schema and Data Features
    <OTHER> -> TestFilter_12
TestFilter_12
    DEFAULT_VALUE = <UNFILTERED>
    TEST_LIST = "BOOL_OP,OR,COMPOSITE_TEST,""""""1"""""",TEST_CLAUSE,TEST @Value(ISO2) = FR",@Value(ISO2) = FR
    @Value(ISO2) = FR -> FuzzyStringComparer_3
FuzzyStringComparer_3
    DEST_ATTR = matchORnot
    STRING1 = @Value(subregion)
    STRING2 = @Value(county)
    -> TestFilter_11
TestFilter_11
    DEFAULT_VALUE = <UNFILTERED>
    TEST_LIST = "BOOL_OP,OR,COMPOSITE_TEST,""""""1"""""",TEST_CLAUSE,TEST @Value(matchORnot) > 0.95",passed
    passed -> DuplicateFilter_3
DuplicateFilter_3
    INPUT_ORDERED_CHOICE = No
    KEYATTR = region
    UNIQUE -> AttributeManager_37
AttributeManager_37
    ATTR_TABLE:
      REMOVE matchORnot
      REMOVE join
      SET_TO url = @LowerCase(https://download.geofabrik.de/@Value(Continent)/@Value(Country)/@Value(region)-latest.osm.pbf)
    -> DuplicateFilter
DuplicateFilter
    INPUT_ORDERED_CHOICE = No
    KEYATTR = url
    UNIQUE -> AttributeManager_39
AttributeManager_39
    ATTR_TABLE = SET_TO join = 0
    -> FeatureJoiner [LEFT]
CoordinateExtractor_2
    IND = 0
    MODE = Specify Coordinate
    X_ATTR = _x
    Y_ATTR = _y
    -> AttributeManager_40
AttributeManager_40
    ATTR_TABLE:
      REMOVE min_x
      REMOVE min_y
      REMOVE max_x
      REMOVE max_y
      SET_TO join = 0
      SET_TO max_x = @Evaluate(@Value(_x)+@Value(_length.max))
      SET_TO min_x = @Value(_x)
      SET_TO max_y = @Value(_y)
      SET_TO min_y = @Evaluate(@Value(_y)-@Value(_length.max))
    -> FeatureJoiner [RIGHT]
FeatureJoiner
    ATTR_CONFLICT_RES = Use Left
    GEOMETRY_HANDLING = Use Left
    JOIN_KEYS = join join AUTO
    JOIN_MODE = Inner
    JOINED -> ISO_merger [AttributeManager]
ISO_merger
    AREA_KM2 = @Value(area_km2)
    B_PER_CAP = @Value(b_per_cap)
    CONTINENT = @Value(Continent)
    COUNTRY = @Value(country)
    COUNTRY_2 = @Value(Country)
    COUNTRY_COMP = @Value(Country_comp)
    COUNTY = @Value(county)
    IDH = @Value(IDH)
    ISO2 = @Value(ISO2)
    ISO3 = @Value(ISO3)
    JOIN = @Value(join)
    LAT_LON = @Value(lat_lon)
    MAX_X = @Value(max_x)
    MAX_Y = @Value(max_y)
    MIN_X = @Value(min_x)
    MIN_Y = @Value(min_y)
    OSMFR = @Value(OSMFR)
    POPDENS_CAP_KM2 = @Value(PopDens_cap_km2)
    POPULATION = @Value(Population)
    REGION = @Value(region)
    SIZE_MB = @Value(Size_MB)
    STATE = @Value(state)
    STATEANDCOUNTRY = @Value(stateANDcountry)
    SUBREGION = @Value(subregion)
    URL = @Value(url)
    _COPYNUM = @Value(_copynum)
    _CREATION_INSTANCE = @Value(_creation_instance)
    _LENGTH = @Value(_length)
    _LENGTH.MAX = @Value(_length.max)
    _OVERLAPS = @Value(_overlaps)
    _X = @Value(_x)
    _Y = @Value(_y)
    AttributeManager_126_:_Output -> DuplicateFilter_5
    AttributeManager_126_:_Output -> URL_managment [Counter]
    DuplicateFilter_4_:_Unique -> AttributeManager_124
    DuplicateFilter_4_:_Unique -> Weather_report
    DuplicateFilter_4_:_Unique -> DEM
    DuplicateFilter_4_:_Unique -> PopDens1km
DuplicateFilter_5
    INPUT_ORDERED_CHOICE = No
    KEYATTR = ISO3
    UNIQUE -> AttributeManager_57
    UNIQUE -> AttributeManager_74
    UNIQUE -> FeatureReader_5 [INITIATOR]
FeatureReader_5
    ATTR_ACCUM_MODE = Only Use Result
    COMBINE_GEOM = Use Result
    CSV2_CASE_SENSITIVE_FIELD_NAMES = Yes
    CSV2_CHUNK_SIZE = 100000
    CSV2_DATA_START_LINE = 2
    CSV2_DATE_INPUT_FORMAT = FME
    CSV2_DELIMITER = auto
    CSV2_ENCODING = windows-1252
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = Yes
    CSV2_SCAN_ADDITIONAL_FIELDS = No
    CSV2_SCAN_MAX_ROWS = 10000
    CSV2_SCAN_TYPES = Yes
    CSV2_SKIP_DUPLICATE_DELIMITERS = No
    CSV2_STRING_TYPE_ATTRIBUTE_HANDLING = EXPLICIT_WIDTH
    CSV2_SUPPORTED_READER_ARCHIVE_EXTENSIONS = csv.gz,txt.gz
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_TYPE_ATTRIBUTE_HANDLING = STANDARD_TYPES
    CSV2_USE_CUSTOM_SCHEMA = NO
    DATASET = $(EXCEL_FILES_SOURCE)\quality_OSM.csv
    FORMAT = CSV2
    INTERACT = NONE
    OUTPUT_FEATURES_DISPLAY = Schema and Data Features
PopDensity100m: WorkspaceRunner
    BLOCKING = No
    MAX_TO_BATCH = 1
    WORKSPACE_FILE = $(FME_MF_DIR)popDens100m_tif2tifv2.fmw
    WORKSPACE_PARAMETERS = URL_DL_1,@Value(url1),URL_DL_2,@Value(url2),URL_DL_3,@Value(url3),URL_DL_4,@Value(url4),URL_DL_5,@Value(url5),URL_DL_6,@Value(url6),URL_DL_7,@Value(url7),URL_DL_8,@Value(url7),ISO_code,@Value(ISO3),GEOM,@Value(min_x) @Value(min_y) @Value(max_x) @Value(max_y),DestDataset_GEOTIFF,$(FME_MF_DIR_USERTYPED)output_@Value(ISO3)\03_Population_Density,year_last,2020
AttributeManager_57
    ATTR_TABLE:
      REMOVE url
      REMOVE max_x
      REMOVE min_x
      REMOVE max_y
      REMOVE min_y
      SET_TO Date_extraction = @DateTimeNow()
      SET_TO Date_extraction = @DateTimeFormat(@Value(Date_extraction),%d-%m-%Y)
    -> Contribution_OSM_evolution
Contribution_OSM_evolution: WorkspaceRunner
    BLOCKING = No
    MAX_TO_BATCH = 1
    WORKSPACE_FILE = $(FME_MF_DIR)contribution_evolution.fmw
    WORKSPACE_PARAMETERS = ISO3,@Value(ISO3),END_DATE,@Value(Date_extraction),SourceDataset_CSV2,$(EXCEL_FILES_SOURCE)\quality_OSM.csv,DestDataset_PNGRASTER,$(FME_MF_DIR_USERTYPED)output_@Value(ISO_merge)\00_SUMMARY
PopDens1km: WorkspaceRunner
    BLOCKING = Yes
    WORKSPACE_FILE = $(FME_MF_DIR)popDens_tif2tifv2.fmw
    WORKSPACE_PARAMETERS = SourceDataset_GEOTIFF,$(FME_MF_DIR_USERTYPED)EXEL_FILES\ppp_2020_1km_Aggregated.tif,DestDataset_GEOTIFF,$(FME_MF_DIR_USERTYPED)output_@Value(ISO_merge)\03_Population_Density,DestDataset_TEXTLINE,$(FME_MF_DIR_USERTYPED)output_@Value(ISO_merge)\03_Population_density\pop_dens_BB.txt,ISO_code,@Value(ISO_merge),GEOM,@Value(min_x) @Value(min_y) @Value(max_x) @Value(max_y)
    SUCCEEDED -> FeatureReader [INITIATOR]
FeatureReader
    ATTR_ACCUM_MODE = Merge Initiator and Result
    ATTR_CONFLICT_RES = Use Result
    ATTR_IGNORE_NULLS = No
    COMBINE_GEOM = Use Result
    DATASET = $(FME_MF_DIR_USERTYPED)output_@Value(ISO_merge)\03_Population_density\pop_dens_BB.txt
    FORMAT = TEXTLINE
    OUTPUT_FEATURES_DISPLAY = Schema and Data Features
    TEXTLINE_CREATE_FEATURE_TABLES_FROM_DATA = Yes
    TEXTLINE_ENCODING = windows-1252
    TEXTLINE_READ_BOTTOM_UP = No
    TEXTLINE_READ_WHOLE_FILE_AT_ONCE = NO
    TEXTLINE_SKIP_FOOTER = 0
    TEXTLINE_SKIP_LINES = 0
    <OTHER> -> AttributeExposer
AttributeExposer
    ATTR_LIST = text_line_data
    -> AttributeManager_58
AttributeManager_58
    ATTR_TABLE:
      RENAME_SET_VALUE text_line_data > Population_Density
      REMOVE url
DEM: WorkspaceRunner
    BLOCKING = Yes
    WORKSPACE_FILE = $(FME_MF_DIR)DEM_geotiff2geotiffv2.fmw
    WORKSPACE_PARAMETERS = DestDataset_GEOTIFF,$(FME_MF_DIR_USERTYPED)output_@Value(ISO_merge)\02_DEM,GEOM_minLON,@Value(min_x),GEOM_minLAT,@Value(min_y),GEOM_maxLAT,@Value(max_y),GEOM_maxLON,@Value(max_x),ISO_code,@Value(ISO_merge)
Weather_report: WorkspaceRunner
    BLOCKING = No
    MAX_TO_BATCH = 1
    WORKSPACE_FILE = $(FME_MF_DIR)Weather_extractor.fmw
    WORKSPACE_PARAMETERS = GEOM,@Value(min_x) @Value(min_y) @Value(max_x) @Value(max_y),ISO3,@Value(ISO_merge),DestDataset_PNGRASTER,$(FME_MF_DIR_USERTYPED)output_@Value(ISO_merge)\04_Weather_report,DestDataset_CSV2,$(FME_MF_DIR_USERTYPED)output_@Value(ISO_merge)\04_Weather_report\prevision_data
URL_managment: URL managment
    ISO3 = @Value(ISO3)
    MAX_X = @Value(max_x)
    MAX_Y = @Value(max_y)
    MIN_X = @Value(min_x)
    MIN_Y = @Value(min_y)
    URL = @Value(url)
    AttributeManager_52_:_Output -> OSM
    AttributeManager_51_:_Output -> OSM
    AttributeManager_50_:_Output -> OSM
    AttributeManager_53_:_Output -> OSM
    AttributeManager_54_:_Output -> OSM
    AttributeManager_55_:_Output -> OSM
    AttributeManager_56_:_Output -> OSM
OSM: WorkspaceRunner
    BLOCKING = Yes
    WORKSPACE_FILE = $(FME_MF_DIR)OSM_basic_v1_2.fmw
    WORKSPACE_PARAMETERS = FEATURETYPES,$(OSM_features),URL_DL_1,@Value(url1),URL_DL_2,@Value(url2),URL_DL_3,@Value(url3),URL_DL_4,@Value(url4),URL_DL_5,@Value(url5),URL_DL_6,@Value(url6),URL_DL_7,@Value(url7),URL_DL_8,@Value(url8),ISO_code,@Value(ISO_merge),GEOM,@Value(min_x) @Value(min_y) @Value(max_x) @Value(max_y),DestDataset_SHAPEFILE,$(FME_MF_DIR_USERTYPED)output_@Value(ISO_merge)\01_OSM\aerialway,DestDataset_SHAPEFILE_41,$(FME_MF_DIR_USERTYPED)output_@Value(ISO_merge)\01_OSM\aeroway,DestDataset_SHAPEFILE_57,$(FME_MF_DIR_USERTYPED)output_@Value(ISO_merge)\01_OSM\boundary,DestDataset_SHAPEFILE_37,$(FME_MF_DIR_USERTYPED)output_@Value(ISO_merge)\01_OSM\building,DestDataset_SHAPEFILE_45,$(FME_MF_DIR_USERTYPED)output_@Value(ISO_merge)\01_OSM\place,DestDataset_SHAPEFILE_53,$(FME_MF_DIR_USERTYPED)output_@Value(ISO_merge)\01_OSM\amenity,DestDataset_SHAPEFILE_31,$(FME_MF_DIR_USERTYPED)output_@Value(ISO_merge)\01_OSM\barrier,DestDataset_SHAPEFILE_35,$(FME_MF_DIR_USERTYPED)output_@Value(ISO_merge)\01_OSM\craft,DestDataset_SHAPEFILE_39,$(FME_MF_DIR_USERTYPED)output_@Value(ISO_merge)\01_OSM\emergency,DestDataset_SHAPEFILE_43,$(FME_MF_DIR_USERTYPED)output_@Value(ISO_merge)\01_OSM\historic,DestDataset_SHAPEFILE_47,$(FME_MF_DIR_USERTYPED)output_@Value(ISO_merge)\01_OSM\geological,DestDataset_SHAPEFILE_51,$(FME_MF_DIR_USERTYPED)output_@Value(ISO_merge)\01_OSM\landusel,DestDataset_SHAPEFILE_55,$(FME_MF_DIR_USERTYPED)output_@Value(ISO_merge)\01_OSM\leisure,DestDataset_SHAPEFILE_30,$(FME_MF_DIR_USERTYPED)output_@Value(ISO_merge)\01_OSM\man_made,DestDataset_SHAPEFILE_32,$(FME_MF_DIR_USERTYPED)output_@Value(ISO_merge)\01_OSM\military,DestDataset_SHAPEFILE_34,$(FME_MF_DIR_USERTYPED)output_@Value(ISO_merge)\01_OSM\natural,DestDataset_SHAPEFILE_36,$(FME_MF_DIR_USERTYPED)output_@Value(ISO_merge)\01_OSM\office,DestDataset_SHAPEFILE_38,$(FME_MF_DIR_USERTYPED)output_@Value(ISO_merge)\01_OSM\power,DestDataset_SHAPEFILE_40,$(FME_MF_DIR_USERTYPED)output_@Value(ISO_merge)\01_OSM\public_transport,DestDataset_SHAPEFILE_42,$(FME_MF_DIR_USERTYPED)output_@Value(ISO_merge)\01_OSM\railway,DestDataset_SHAPEFILE_44,$(FME_MF_DIR_USERTYPED)output_@Value(ISO_merge)\01_OSM\route,DestDataset_SHAPEFILE_46,$(FME_MF_DIR_USERTYPED)output_@Value(ISO_merge)\01_OSM\shop,DestDataset_SHAPEFILE_48,$(FME_MF_DIR_USERTYPED)output_@Value(ISO_merge)\01_OSM\sport,DestDataset_SHAPEFILE_50,$(FME_MF_DIR_USERTYPED)output_@Value(ISO_merge)\01_OSM\tourism,DestDataset_SHAPEFILE_52,$(FME_MF_DIR_USERTYPED)output_@Value(ISO_merge)\01_OSM\waterway,DestDataset_SHAPEFILE_54,$(FME_MF_DIR_USERTYPED)output_@Value(ISO_merge)\01_OSM\highway,DestDataset_TEXTLINE,$(FME_MF_DIR_USERTYPED)output_@Value(ISO_merge)\00_SUMMARY\summary_features.txt
AttributeManager_124
    ATTR_TABLE = SET_TO join = 0
    -> FeatureJoiner_53 [RIGHT]
WorkspaceRunner
    BLOCKING = Yes
    WORKSPACE_FILE = $(FME_MF_DIR)worker1.fmw
    WORKSPACE_PARAMETERS = PARAMETER1,asDSA
Creator_7
    GEOMTYPE = Geometry Object
    NUM = 250
    CREATED -> AttributeManager_119
AttributeManager_119
    ATTR_TABLE = SET_TO join = 0
    -> FeatureJoiner_50 [LEFT]
FeatureJoiner_50
    ATTR_CONFLICT_RES = Use Left
    GEOMETRY_HANDLING = Use Left
    JOIN_KEYS = join _copynum AUTO
    JOIN_MODE = Full
    JOINED -> RandomNumberGenerator
    JOINED -> TestFilter_23
RandomNumberGenerator
    MAX = @Value(max_x)
    MIN = @Value(min_x)
    PLACES = 5
    RESULT_ATTR = _random_number
    -> RandomNumberGenerator_2
RandomNumberGenerator_2
    MAX = @Value(max_y)
    MIN = @Value(min_y)
    PLACES = 5
    RESULT_ATTR = _random_number2
    -> AttributeManager_115
AttributeManager_115
    ATTR_TABLE:
      SET_TO zoom = 10
      REMOVE min_x
      REMOVE min_y
      REMOVE max_x
      REMOVE max_y
      REMOVE lat_lon
      REMOVE _overlaps
      RENAME_SET_VALUE _random_number > lon_deg
      RENAME_SET_VALUE _random_number2 > lat_deg
    -> FeatureJoiner_52 [RIGHT]
TestFilter_23
    DEFAULT_VALUE = <UNFILTERED>
    TEST_LIST = "BOOL_OP,OR,COMPOSITE_TEST,""""""1"""""",TEST_CLAUSE,TEST @Value(_creation_instance) = 0",@Value(_copynum) = 0
    @Value(_copynum) = 0 -> AttributeManager_120
AttributeManager_120
    ATTR_TABLE:
      REMOVE _creation_instance
      REMOVE join
      REMOVE _min_max_BB{}
      REMOVE min_x
      REMOVE min_y
      REMOVE max_x
      REMOVE max_y
      REMOVE _copynum
      REMOVE lat_lon
      REMOVE _length
      SET_TO _length.max = @Evaluate(@Value(_length.max)*111)
      REMOVE _overlaps
      SET_TO join = 0
    -> FeatureJoiner_51 [RIGHT]
Creator_2
    GEOMTYPE = Geometry Object
    NUM = 1
    CREATED -> HTTPCaller
HTTPCaller
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://api.openweathermap.org/data/2.5/forecast?lat=45.83027317866976&lon=6.865267023082311&appid=beeb9ce4829f91765be3060efde0af4c
    TRANSFER_TIMEOUT_LENGTH = 90
    USE_COOKIES = No
    VERIFY_SSL_CERTIFICATES = Yes
    -> AttributeKeeper
Note: https://community.safe.com/s/article/json-transformations
AttributeKeeper
    CREATE_BULK_MODE_FEATURES = NO
    KEEP_ATTRS = _response_body
    -> JSONFlattener
JSONFlattener
    ERROR_LIST_ATTR = _json_error
    JSON_DOCUMENT = @Value(_response_body)
    READ_FROM_FILE = NO
    RECURSIVE = Yes
    -> StringReplacer_9
StringReplacer_9
    CASE = NO
    FIND_TEXT = "snow":{"3h"
    NO_MATCH = _FME_NO_OP_
    REGEXP = NO
    REPLACE_TEXT = "snow":{"3h_s"
    SRC_ATTRS = _response_body
    -> JSONFragmenter
JSONFragmenter
    EXPLODE_FORMAT = JSON
    EXTRACT_ATTR = No
    JSON_ATTR = _response_body
    JSON_QUERY = json[*]
    READ_FROM_FILE = NO
    REJECT_EMPTY_LISTS = YES
    FRAGMENTS -> JSONFragmenter_2
Creator_6
    GEOMTYPE = Geometry Object
    NUM = 16
    CREATED -> AttributeManager_121
AttributeManager_121
    ATTR_TABLE = SET_TO join = 0
    -> FeatureJoiner_51 [LEFT]
FeatureJoiner_51
    ATTR_CONFLICT_RES = Use Left
    GEOMETRY_HANDLING = Use Left
    JOIN_KEYS = join join AUTO
    JOIN_MODE = Full
    JOINED -> AttributeManager_116
AttributeManager_116
    ATTR_TABLE = SET_TO to_minimize = @Evaluate(@abs((111*360)/(@pow(2,@Value(_creation_instance)))-@Value(_length.max)) + 1)
    -> StatisticsCalculator_5
StatisticsCalculator_5
    CALCULATION_MODE = NUMERIC
    FEAT_STATS = to_minimize,NUMERIC_MODE,MIN,,,,,,,,,,,,
    COMPLETE -> TestFilter_22
TestFilter_22
    DEFAULT_VALUE = <UNFILTERED>
    TEST_LIST = "BOOL_OP,OR,COMPOSITE_TEST,""""""1"""""",TEST_CLAUSE,TEST @Value(to_minimize) = @Value(to_minimize.min)",@Value(to_minimize) = @Value(to_minimize.min)
    @Value(to_minimize) = @Value(to_minimize.min) -> AttributeManager_117
AttributeManager_117
    ATTR_TABLE:
      RENAME_SET_VALUE _creation_instance > zoom
      REMOVE to_minimize
      REMOVE to_minimize.min
      REMOVE _length.max
    -> FeatureJoiner_52 [LEFT]
FeatureJoiner_52
    ATTR_CONFLICT_RES = Use Left
    GEOMETRY_HANDLING = Use Left
    JOIN_KEYS = join join AUTO
    JOIN_MODE = Inner
    JOINED -> deg2num
deg2num
    LAT_DEG = @Value(lat_deg)
    LON_DEG = @Value(lon_deg)
    ZOOM = @Value(zoom)
    -> AttributeManager_123
AttributeManager_123
    ATTR_TABLE = SET_TO ytile_b = @Evaluate(@Value(ytile)+1)
    -> num2deg
num2deg
    LAT_DEG = @Value(lat_deg)
    LON_DEG = @Value(lon_deg)
    XTILE = @Value(xtile)
    YTILE = @Value(ytile)
    YTILE_B = @Value(ytile_b)
    ZOOM = @Value(zoom)
    _CREATION_INSTANCE = @Value(_creation_instance)
    -> AttributeManager_118
AttributeManager_118
    ATTR_TABLE:
      RENAME_SET_VALUE lat_deg > lat_deg_tile
      RENAME_SET_VALUE lon_deg > lon_deg_tile
      REMOVE ytile_b
      RENAME_SET_VALUE lat_deg_b > lat_deg_tile_b
    -> DuplicateFilter_7
DuplicateFilter_7
    INPUT_ORDERED_CHOICE = No
    KEYATTR = lat_deg_tile lon_deg_tile xtile ytile
    UNIQUE -> Sorter
Sorter
    SORT_PARM = xtile NUMERIC ASCENDING ytile NUMERIC ASCENDING
    SORTED -> Joiner_custom [WorkspaceRunner_2_Input]
Joiner_custom
    LAT_DEG_TILE = @Value(lat_deg_tile)
    LAT_DEG_TILE_B = @Value(lat_deg_tile_b)
    LON_DEG_TILE = @Value(lon_deg_tile)
    XTILE = @Value(xtile)
    YTILE = @Value(ytile)
    ZOOM = @Value(zoom)
    -> AttributeManager_122
AttributeManager_122
    ATTR_TABLE:
      SET_TO join = 0
      SET_TO lat_deg_tile2 = FME_CONDITIONAL:DEFAULT_VALUE'_FME_NO_OP_'BOOL_OP;OR;COMPOSITE_TEST;1;TEST lat_deg_tile2 ATTRIBUTE_IS_MISSING _FME_BLANK_STRING_'@Value(lat_deg_tile1)'FME_NUM_CONDITIONS2___
      SET_TO lon_deg_tile2 = FME_CONDITIONAL:DEFAULT_VALUE'_FME_NO_OP_'BOOL_OP;OR;COMPOSITE_TEST;1;TEST lon_deg_tile2 ATTRIBUTE_IS_MISSING _FME_BLANK_STRING_'@Value(lon_deg_tile1)'FME_NUM_CONDITIONS2___
      SET_TO xtile2 = FME_CONDITIONAL:DEFAULT_VALUE'_FME_NO_OP_'BOOL_OP;OR;COMPOSITE_TEST;1;TEST xtile2 ATTRIBUTE_IS_MISSING _FME_BLANK_STRING_'@Value(xtile1)'FME_NUM_CONDITIONS2___
      SET_TO ytile2 = FME_CONDITIONAL:DEFAULT_VALUE'_FME_NO_OP_'BOOL_OP;OR;COMPOSITE_TEST;1;TEST ytile2 ATTRIBUTE_IS_MISSING _FME_BLANK_STRING_'@Value(ytile1)'FME_NUM_CONDITIONS2___
      SET_TO lat_deg_tile3 = FME_CONDITIONAL:DEFAULT_VALUE'_FME_NO_OP_'BOOL_OP;OR;COMPOSITE_TEST;1;TEST lat_deg_tile3 ATTRIBUTE_IS_MISSING _FME_BLANK_STRING_'@Value(lat_deg_tile1)'FME_NUM_CONDITIONS2___
      SET_TO lon_deg_tile3 = FME_CONDITIONAL:DEFAULT_VALUE'_FME_NO_OP_'BOOL_OP;OR;COMPOSITE_TEST;1;TEST lon_deg_tile3 ATTRIBUTE_IS_MISSING _FME_BLANK_STRING_'@Value(lon_deg_tile1)'FME_NUM_CONDITIONS2___
      SET_TO xtile3 = FME_CONDITIONAL:DEFAULT_VALUE'_FME_NO_OP_'BOOL_OP;OR;COMPOSITE_TEST;1;TEST xtile3 ATTRIBUTE_IS_MISSING _FME_BLANK_STRING_'@Value(xtile1)'FME_NUM_CONDITIONS2___
      SET_TO ytile3 = FME_CONDITIONAL:DEFAULT_VALUE'_FME_NO_OP_'BOOL_OP;OR;COMPOSITE_TEST;1;TEST ytile3 ATTRIBUTE_IS_MISSING _FME_BLANK_STRING_'@Value(ytile1)'FME_NUM_CONDITIONS2___
      SET_TO lat_deg_tile4 = FME_CONDITIONAL:DEFAULT_VALUE'_FME_NO_OP_'BOOL_OP;OR;COMPOSITE_TEST;1;TEST lat_deg_tile4 ATTRIBUTE_IS_MISSING _FME_BLANK_STRING_'@Value(lat_deg_tile1)'FME_NUM_CONDITIONS2___
      SET_TO lon_deg_tile4 = FME_CONDITIONAL:DEFAULT_VALUE'_FME_NO_OP_'BOOL_OP;OR;COMPOSITE_TEST;1;TEST lon_deg_tile4 ATTRIBUTE_IS_MISSING _FME_BLANK_STRING_'@Value(lon_deg_tile1)'FME_NUM_CONDITIONS2___
      SET_TO xtile4 = FME_CONDITIONAL:DEFAULT_VALUE'_FME_NO_OP_'BOOL_OP;OR;COMPOSITE_TEST;1;TEST xtile4 ATTRIBUTE_IS_MISSING _FME_BLANK_STRING_'@Value(xtile1)'FME_NUM_CONDITIONS2___
      SET_TO ytile4 = FME_CONDITIONAL:DEFAULT_VALUE'_FME_NO_OP_'BOOL_OP;OR;COMPOSITE_TEST;1;TEST ytile4 ATTRIBUTE_IS_MISSING _FME_BLANK_STRING_'@Value(ytile1)'FME_NUM_CONDITIONS2___
      SET_TO lat_deg_tile5 = FME_CONDITIONAL:DEFAULT_VALUE'_FME_NO_OP_'BOOL_OP;OR;COMPOSITE_TEST;1;TEST lat_deg_tile5 ATTRIBUTE_IS_MISSING _FME_BLANK_STRING_'@Value(lat_deg_tile1)'FME_NUM_CONDITIONS2___
      SET_TO lon_deg_tile5 = FME_CONDITIONAL:DEFAULT_VALUE'_FME_NO_OP_'BOOL_OP;OR;COMPOSITE_TEST;1;TEST lon_deg_tile5 ATTRIBUTE_IS_MISSING _FME_BLANK_STRING_'@Value(lon_deg_tile1)'FME_NUM_CONDITIONS2___
      SET_TO xtile5 = FME_CONDITIONAL:DEFAULT_VALUE'_FME_NO_OP_'BOOL_OP;OR;COMPOSITE_TEST;1;TEST xtile5 ATTRIBUTE_IS_MISSING _FME_BLANK_STRING_'@Value(xtile1)'FME_NUM_CONDITIONS2___
      SET_TO ytile5 = FME_CONDITIONAL:DEFAULT_VALUE'_FME_NO_OP_'BOOL_OP;OR;COMPOSITE_TEST;1;TEST ytile5 ATTRIBUTE_IS_MISSING _FME_BLANK_STRING_'@Value(ytile1)'FME_NUM_CONDITIONS2___
      SET_TO lat_deg_tile6 = FME_CONDITIONAL:DEFAULT_VALUE'_FME_NO_OP_'BOOL_OP;OR;COMPOSITE_TEST;1;TEST lat_deg_tile6 ATTRIBUTE_IS_MISSING _FME_BLANK_STRING_'@Value(lat_deg_tile1)'FME_NUM_CONDITIONS2___
      SET_TO lon_deg_tile6 = FME_CONDITIONAL:DEFAULT_VALUE'_FME_NO_OP_'BOOL_OP;OR;COMPOSITE_TEST;1;TEST lon_deg_tile6 ATTRIBUTE_IS_MISSING _FME_BLANK_STRING_'@Value(lon_deg_tile1)'FME_NUM_CONDITIONS2___
      SET_TO xtile6 = FME_CONDITIONAL:DEFAULT_VALUE'_FME_NO_OP_'BOOL_OP;OR;COMPOSITE_TEST;1;TEST xtile6 ATTRIBUTE_IS_MISSING _FME_BLANK_STRING_'@Value(xtile1)'FME_NUM_CONDITIONS2___
      SET_TO ytile6 = FME_CONDITIONAL:DEFAULT_VALUE'_FME_NO_OP_'BOOL_OP;OR;COMPOSITE_TEST;1;TEST ytile6 ATTRIBUTE_IS_MISSING _FME_BLANK_STRING_'@Value(ytile1)'FME_NUM_CONDITIONS2___
      SET_TO lat_deg_tile7 = FME_CONDITIONAL:DEFAULT_VALUE'_FME_NO_OP_'BOOL_OP;OR;COMPOSITE_TEST;1;TEST lat_deg_tile7 ATTRIBUTE_IS_MISSING _FME_BLANK_STRING_'@Value(lat_deg_tile1)'FME_NUM_CONDITIONS2___
      SET_TO lon_deg_tile7 = FME_CONDITIONAL:DEFAULT_VALUE'_FME_NO_OP_'BOOL_OP;OR;COMPOSITE_TEST;1;TEST lon_deg_tile7 ATTRIBUTE_IS_MISSING _FME_BLANK_STRING_'@Value(lon_deg_tile1)'FME_NUM_CONDITIONS2___
      SET_TO xtile7 = FME_CONDITIONAL:DEFAULT_VALUE'_FME_NO_OP_'BOOL_OP;OR;COMPOSITE_TEST;1;TEST xtile7 ATTRIBUTE_IS_MISSING _FME_BLANK_STRING_'@Value(xtile1)'FME_NUM_CONDITIONS2___
      SET_TO ytile7 = FME_CONDITIONAL:DEFAULT_VALUE'_FME_NO_OP_'BOOL_OP;OR;COMPOSITE_TEST;1;TEST ytile7 ATTRIBUTE_IS_MISSING _FME_BLANK_STRING_'@Value(ytile1)'FME_NUM_CONDITIONS2___
      SET_TO lat_deg_tile8 = FME_CONDITIONAL:DEFAULT_VALUE'_FME_NO_OP_'BOOL_OP;OR;COMPOSITE_TEST;1;TEST lat_deg_tile8 ATTRIBUTE_IS_MISSING _FME_BLANK_STRING_'@Value(lat_deg_tile1)'FME_NUM_CONDITIONS2___
      SET_TO lon_deg_tile8 = FME_CONDITIONAL:DEFAULT_VALUE'_FME_NO_OP_'BOOL_OP;OR;COMPOSITE_TEST;1;TEST lon_deg_tile8 ATTRIBUTE_IS_MISSING _FME_BLANK_STRING_'@Value(lon_deg_tile1)'FME_NUM_CONDITIONS2___
      SET_TO xtile8 = FME_CONDITIONAL:DEFAULT_VALUE'_FME_NO_OP_'BOOL_OP;OR;COMPOSITE_TEST;1;TEST xtile8 ATTRIBUTE_IS_MISSING _FME_BLANK_STRING_'@Value(xtile1)'FME_NUM_CONDITIONS2___
      SET_TO ytile8 = FME_CONDITIONAL:DEFAULT_VALUE'_FME_NO_OP_'BOOL_OP;OR;COMPOSITE_TEST;1;TEST ytile8 ATTRIBUTE_IS_MISSING _FME_BLANK_STRING_'@Value(ytile1)'FME_NUM_CONDITIONS2___
      SET_TO lat_deg_tile9 = FME_CONDITIONAL:DEFAULT_VALUE'_FME_NO_OP_'BOOL_OP;OR;COMPOSITE_TEST;1;TEST lat_deg_tile9 ATTRIBUTE_IS_MISSING _FME_BLANK_STRING_'@Value(lat_deg_tile1)'FME_NUM_CONDITIONS2___
      SET_TO lon_deg_tile9 = FME_CONDITIONAL:DEFAULT_VALUE'_FME_NO_OP_'BOOL_OP;OR;COMPOSITE_TEST;1;TEST lon_deg_tile9 ATTRIBUTE_IS_MISSING _FME_BLANK_STRING_'@Value(lon_deg_tile1)'FME_NUM_CONDITIONS2___
      SET_TO xtile9 = FME_CONDITIONAL:DEFAULT_VALUE'_FME_NO_OP_'BOOL_OP;OR;COMPOSITE_TEST;1;TEST xtile9 ATTRIBUTE_IS_MISSING _FME_BLANK_STRING_'@Value(xtile1)'FME_NUM_CONDITIONS2___
      SET_TO ytile9 = FME_CONDITIONAL:DEFAULT_VALUE'_FME_NO_OP_'BOOL_OP;OR;COMPOSITE_TEST;1;TEST ytile9 ATTRIBUTE_IS_MISSING _FME_BLANK_STRING_'@Value(ytile1)'FME_NUM_CONDITIONS2___
      SET_TO lat_deg_tile10 = FME_CONDITIONAL:DEFAULT_VALUE'_FME_NO_OP_'BOOL_OP;OR;COMPOSITE_TEST;1;TEST lat_deg_tile10 ATTRIBUTE_IS_MISSING _FME_BLANK_STRING_'@Value(lat_deg_tile1)'FME_NUM_CONDITIONS2___
      SET_TO lon_deg_tile10 = FME_CONDITIONAL:DEFAULT_VALUE'_FME_NO_OP_'BOOL_OP;OR;COMPOSITE_TEST;1;TEST lon_deg_tile10 ATTRIBUTE_IS_MISSING _FME_BLANK_STRING_'@Value(lon_deg_tile1)'FME_NUM_CONDITIONS2___
      SET_TO xtile10 = FME_CONDITIONAL:DEFAULT_VALUE'_FME_NO_OP_'BOOL_OP;OR;COMPOSITE_TEST;1;TEST xtile10 ATTRIBUTE_IS_MISSING _FME_BLANK_STRING_'@Value(xtile1)'FME_NUM_CONDITIONS2___
      SET_TO ytile10 = FME_CONDITIONAL:DEFAULT_VALUE'_FME_NO_OP_'BOOL_OP;OR;COMPOSITE_TEST;1;TEST ytile10 ATTRIBUTE_IS_MISSING _FME_BLANK_STRING_'@Value(ytile1)'FME_NUM_CONDITIONS2___
      SET_TO lat_deg_tile11 = FME_CONDITIONAL:DEFAULT_VALUE'_FME_NO_OP_'BOOL_OP;OR;COMPOSITE_TEST;1;TEST lat_deg_tile11 ATTRIBUTE_IS_MISSING _FME_BLANK_STRING_'@Value(lat_deg_tile1)'FME_NUM_CONDITIONS2___
      SET_TO lon_deg_tile11 = FME_CONDITIONAL:DEFAULT_VALUE'_FME_NO_OP_'BOOL_OP;OR;COMPOSITE_TEST;1;TEST lon_deg_tile11 ATTRIBUTE_IS_MISSING _FME_BLANK_STRING_'@Value(lon_deg_tile1)'FME_NUM_CONDITIONS2___
      SET_TO xtile11 = FME_CONDITIONAL:DEFAULT_VALUE'_FME_NO_OP_'BOOL_OP;OR;COMPOSITE_TEST;1;TEST xtile11 ATTRIBUTE_IS_MISSING _FME_BLANK_STRING_'@Value(xtile1)'FME_NUM_CONDITIONS2___
      SET_TO ytile11 = FME_CONDITIONAL:DEFAULT_VALUE'_FME_NO_OP_'BOOL_OP;OR;COMPOSITE_TEST;1;TEST ytile11 ATTRIBUTE_IS_MISSING _FME_BLANK_STRING_'@Value(ytile1)'FME_NUM_CONDITIONS2___
      SET_TO lat_deg_tile12 = FME_CONDITIONAL:DEFAULT_VALUE'_FME_NO_OP_'BOOL_OP;OR;COMPOSITE_TEST;1;TEST lat_deg_tile12 ATTRIBUTE_IS_MISSING _FME_BLANK_STRING_'@Value(lat_deg_tile1)'FME_NUM_CONDITIONS2___
      SET_TO lon_deg_tile12 = FME_CONDITIONAL:DEFAULT_VALUE'_FME_NO_OP_'BOOL_OP;OR;COMPOSITE_TEST;1;TEST lon_deg_tile12 ATTRIBUTE_IS_MISSING _FME_BLANK_STRING_'@Value(lon_deg_tile1)'FME_NUM_CONDITIONS2___
      SET_TO xtile12 = FME_CONDITIONAL:DEFAULT_VALUE'_FME_NO_OP_'BOOL_OP;OR;COMPOSITE_TEST;1;TEST xtile12 ATTRIBUTE_IS_MISSING _FME_BLANK_STRING_'@Value(xtile1)'FME_NUM_CONDITIONS2___
      SET_TO ytile12 = FME_CONDITIONAL:DEFAULT_VALUE'_FME_NO_OP_'BOOL_OP;OR;COMPOSITE_TEST;1;TEST ytile12 ATTRIBUTE_IS_MISSING _FME_BLANK_STRING_'@Value(ytile1)'FME_NUM_CONDITIONS2___
      SET_TO lat_deg_tile13 = FME_CONDITIONAL:DEFAULT_VALUE'_FME_NO_OP_'BOOL_OP;OR;COMPOSITE_TEST;1;TEST lat_deg_tile13 ATTRIBUTE_IS_MISSING _FME_BLANK_STRING_'@Value(lat_deg_tile1)'FME_NUM_CONDITIONS2___
      SET_TO lon_deg_tile13 = FME_CONDITIONAL:DEFAULT_VALUE'_FME_NO_OP_'BOOL_OP;OR;COMPOSITE_TEST;1;TEST lon_deg_tile13 ATTRIBUTE_IS_MISSING _FME_BLANK_STRING_'@Value(lon_deg_tile1)'FME_NUM_CONDITIONS2___
      SET_TO xtile13 = FME_CONDITIONAL:DEFAULT_VALUE'_FME_NO_OP_'BOOL_OP;OR;COMPOSITE_TEST;1;TEST xtile13 ATTRIBUTE_IS_MISSING _FME_BLANK_STRING_'@Value(xtile1)'FME_NUM_CONDITIONS2___
      SET_TO ytile13 = FME_CONDITIONAL:DEFAULT_VALUE'_FME_NO_OP_'BOOL_OP;OR;COMPOSITE_TEST;1;TEST ytile13 ATTRIBUTE_IS_MISSING _FME_BLANK_STRING_'@Value(ytile1)'FME_NUM_CONDITIONS2___
      SET_TO lat_deg_tile14 = FME_CONDITIONAL:DEFAULT_VALUE'_FME_NO_OP_'BOOL_OP;OR;COMPOSITE_TEST;1;TEST lat_deg_tile14 ATTRIBUTE_IS_MISSING _FME_BLANK_STRING_'@Value(lat_deg_tile1)'FME_NUM_CONDITIONS2___
      SET_TO lon_deg_tile14 = FME_CONDITIONAL:DEFAULT_VALUE'_FME_NO_OP_'BOOL_OP;OR;COMPOSITE_TEST;1;TEST lon_deg_tile14 ATTRIBUTE_IS_MISSING _FME_BLANK_STRING_'@Value(lon_deg_tile1)'FME_NUM_CONDITIONS2___
      SET_TO xtile14 = FME_CONDITIONAL:DEFAULT_VALUE'_FME_NO_OP_'BOOL_OP;OR;COMPOSITE_TEST;1;TEST xtile14 ATTRIBUTE_IS_MISSING _FME_BLANK_STRING_'@Value(xtile1)'FME_NUM_CONDITIONS2___
      SET_TO ytile14 = FME_CONDITIONAL:DEFAULT_VALUE'_FME_NO_OP_'BOOL_OP;OR;COMPOSITE_TEST;1;TEST ytile14 ATTRIBUTE_IS_MISSING _FME_BLANK_STRING_'@Value(ytile1)'FME_NUM_CONDITIONS2___
      SET_TO lat_deg_tile15 = FME_CONDITIONAL:DEFAULT_VALUE'_FME_NO_OP_'BOOL_OP;OR;COMPOSITE_TEST;1;TEST lat_deg_tile15 ATTRIBUTE_IS_MISSING _FME_BLANK_STRING_'@Value(lat_deg_tile1)'FME_NUM_CONDITIONS2___
      SET_TO lon_deg_tile15 = FME_CONDITIONAL:DEFAULT_VALUE'_FME_NO_OP_'BOOL_OP;OR;COMPOSITE_TEST;1;TEST lon_deg_tile15 ATTRIBUTE_IS_MISSING _FME_BLANK_STRING_'@Value(lon_deg_tile1)'FME_NUM_CONDITIONS2___
      SET_TO xtile15 = FME_CONDITIONAL:DEFAULT_VALUE'_FME_NO_OP_'BOOL_OP;OR;COMPOSITE_TEST;1;TEST xtile15 ATTRIBUTE_IS_MISSING _FME_BLANK_STRING_'@Value(xtile1)'FME_NUM_CONDITIONS2___
      SET_TO ytile15 = FME_CONDITIONAL:DEFAULT_VALUE'_FME_NO_OP_'BOOL_OP;OR;COMPOSITE_TEST;1;TEST ytile15 ATTRIBUTE_IS_MISSING _FME_BLANK_STRING_'@Value(ytile1)'FME_NUM_CONDITIONS2___
      SET_TO lat_deg_tile16 = FME_CONDITIONAL:DEFAULT_VALUE'_FME_NO_OP_'BOOL_OP;OR;COMPOSITE_TEST;1;TEST lat_deg_tile16 ATTRIBUTE_IS_MISSING _FME_BLANK_STRING_'@Value(lat_deg_tile1)'FME_NUM_CONDITIONS2___
      SET_TO lon_deg_tile16 = FME_CONDITIONAL:DEFAULT_VALUE'_FME_NO_OP_'BOOL_OP;OR;COMPOSITE_TEST;1;TEST lon_deg_tile16 ATTRIBUTE_IS_MISSING _FME_BLANK_STRING_'@Value(lon_deg_tile1)'FME_NUM_CONDITIONS2___
      SET_TO xtile16 = FME_CONDITIONAL:DEFAULT_VALUE'_FME_NO_OP_'BOOL_OP;OR;COMPOSITE_TEST;1;TEST xtile16 ATTRIBUTE_IS_MISSING _FME_BLANK_STRING_'@Value(xtile1)'FME_NUM_CONDITIONS2___
      SET_TO ytile16 = FME_CONDITIONAL:DEFAULT_VALUE'_FME_NO_OP_'BOOL_OP;OR;COMPOSITE_TEST;1;TEST ytile16 ATTRIBUTE_IS_MISSING _FME_BLANK_STRING_'@Value(ytile1)'FME_NUM_CONDITIONS2___
      SET_TO lat_deg_tile17 = FME_CONDITIONAL:DEFAULT_VALUE'_FME_NO_OP_'BOOL_OP;OR;COMPOSITE_TEST;1;TEST lat_deg_tile17 ATTRIBUTE_IS_MISSING _FME_BLANK_STRING_'@Value(lat_deg_tile1)'FME_NUM_CONDITIONS2___
      SET_TO lon_deg_tile17 = FME_CONDITIONAL:DEFAULT_VALUE'_FME_NO_OP_'BOOL_OP;OR;COMPOSITE_TEST;1;TEST lon_deg_tile17 ATTRIBUTE_IS_MISSING _FME_BLANK_STRING_'@Value(lon_deg_tile1)'FME_NUM_CONDITIONS2___
      SET_TO xtile17 = FME_CONDITIONAL:DEFAULT_VALUE'_FME_NO_OP_'BOOL_OP;OR;COMPOSITE_TEST;1;TEST xtile17 ATTRIBUTE_IS_MISSING _FME_BLANK_STRING_'@Value(xtile1)'FME_NUM_CONDITIONS2___
      SET_TO ytile17 = FME_CONDITIONAL:DEFAULT_VALUE'_FME_NO_OP_'BOOL_OP;OR;COMPOSITE_TEST;1;TEST ytile17 ATTRIBUTE_IS_MISSING _FME_BLANK_STRING_'@Value(ytile1)'FME_NUM_CONDITIONS2___
      SET_TO lat_deg_tile18 = FME_CONDITIONAL:DEFAULT_VALUE'_FME_NO_OP_'BOOL_OP;OR;COMPOSITE_TEST;1;TEST lat_deg_tile18 ATTRIBUTE_IS_MISSING _FME_BLANK_STRING_'@Value(lat_deg_tile1)'FME_NUM_CONDITIONS2___
      SET_TO lon_deg_tile18 = FME_CONDITIONAL:DEFAULT_VALUE'_FME_NO_OP_'BOOL_OP;OR;COMPOSITE_TEST;1;TEST lon_deg_tile18 ATTRIBUTE_IS_MISSING _FME_BLANK_STRING_'@Value(lon_deg_tile1)'FME_NUM_CONDITIONS2___
      SET_TO xtile18 = FME_CONDITIONAL:DEFAULT_VALUE'_FME_NO_OP_'BOOL_OP;OR;COMPOSITE_TEST;1;TEST xtile18 ATTRIBUTE_IS_MISSING _FME_BLANK_STRING_'@Value(xtile1)'FME_NUM_CONDITIONS2___
      SET_TO ytile18 = FME_CONDITIONAL:DEFAULT_VALUE'_FME_NO_OP_'BOOL_OP;OR;COMPOSITE_TEST;1;TEST ytile18 ATTRIBUTE_IS_MISSING _FME_BLANK_STRING_'@Value(ytile1)'FME_NUM_CONDITIONS2___
      SET_TO lat_deg_tile19 = FME_CONDITIONAL:DEFAULT_VALUE'_FME_NO_OP_'BOOL_OP;OR;COMPOSITE_TEST;1;TEST lat_deg_tile19 ATTRIBUTE_IS_MISSING _FME_BLANK_STRING_'@Value(lat_deg_tile1)'FME_NUM_CONDITIONS2___
      SET_TO lon_deg_tile19 = FME_CONDITIONAL:DEFAULT_VALUE'_FME_NO_OP_'BOOL_OP;OR;COMPOSITE_TEST;1;TEST lon_deg_tile19 ATTRIBUTE_IS_MISSING _FME_BLANK_STRING_'@Value(lon_deg_tile1)'FME_NUM_CONDITIONS2___
      SET_TO xtile19 = FME_CONDITIONAL:DEFAULT_VALUE'_FME_NO_OP_'BOOL_OP;OR;COMPOSITE_TEST;1;TEST xtile19 ATTRIBUTE_IS_MISSING _FME_BLANK_STRING_'@Value(xtile1)'FME_NUM_CONDITIONS2___
      SET_TO ytile19 = FME_CONDITIONAL:DEFAULT_VALUE'_FME_NO_OP_'BOOL_OP;OR;COMPOSITE_TEST;1;TEST ytile19 ATTRIBUTE_IS_MISSING _FME_BLANK_STRING_'@Value(ytile1)'FME_NUM_CONDITIONS2___
      SET_TO lat_deg_tile20 = FME_CONDITIONAL:DEFAULT_VALUE'_FME_NO_OP_'BOOL_OP;OR;COMPOSITE_TEST;1;TEST lat_deg_tile20 ATTRIBUTE_IS_MISSING _FME_BLANK_STRING_'@Value(lat_deg_tile1)'FME_NUM_CONDITIONS2___
      SET_TO lon_deg_tile20 = FME_CONDITIONAL:DEFAULT_VALUE'_FME_NO_OP_'BOOL_OP;OR;COMPOSITE_TEST;1;TEST lon_deg_tile20 ATTRIBUTE_IS_MISSING _FME_BLANK_STRING_'@Value(lon_deg_tile1)'FME_NUM_CONDITIONS2___
      SET_TO xtile20 = FME_CONDITIONAL:DEFAULT_VALUE'_FME_NO_OP_'BOOL_OP;OR;COMPOSITE_TEST;1;TEST xtile20 ATTRIBUTE_IS_MISSING _FME_BLANK_STRING_'@Value(xtile1)'FME_NUM_CONDITIONS2___
      SET_TO ytile20 = FME_CONDITIONAL:DEFAULT_VALUE'_FME_NO_OP_'BOOL_OP;OR;COMPOSITE_TEST;1;TEST ytile20 ATTRIBUTE_IS_MISSING _FME_BLANK_STRING_'@Value(ytile1)'FME_NUM_CONDITIONS2___
      SET_TO lat_deg_tile21 = FME_CONDITIONAL:DEFAULT_VALUE'_FME_NO_OP_'BOOL_OP;OR;COMPOSITE_TEST;1;TEST lat_deg_tile21 ATTRIBUTE_IS_MISSING _FME_BLANK_STRING_'@Value(lat_deg_tile1)'FME_NUM_CONDITIONS2___
      SET_TO lon_deg_tile21 = FME_CONDITIONAL:DEFAULT_VALUE'_FME_NO_OP_'BOOL_OP;OR;COMPOSITE_TEST;1;TEST lon_deg_tile21 ATTRIBUTE_IS_MISSING _FME_BLANK_STRING_'@Value(lon_deg_tile1)'FME_NUM_CONDITIONS2___
      SET_TO xtile21 = FME_CONDITIONAL:DEFAULT_VALUE'_FME_NO_OP_'BOOL_OP;OR;COMPOSITE_TEST;1;TEST xtile21 ATTRIBUTE_IS_MISSING _FME_BLANK_STRING_'@Value(xtile1)'FME_NUM_CONDITIONS2___
      SET_TO ytile21 = FME_CONDITIONAL:DEFAULT_VALUE'_FME_NO_OP_'BOOL_OP;OR;COMPOSITE_TEST;1;TEST ytile21 ATTRIBUTE_IS_MISSING _FME_BLANK_STRING_'@Value(ytile1)'FME_NUM_CONDITIONS2___
      SET_TO lat_deg_tile22 = FME_CONDITIONAL:DEFAULT_VALUE'_FME_NO_OP_'BOOL_OP;OR;COMPOSITE_TEST;1;TEST lat_deg_tile22 ATTRIBUTE_IS_MISSING _FME_BLANK_STRING_'@Value(lat_deg_tile1)'FME_NUM_CONDITIONS2___
      SET_TO lon_deg_tile22 = FME_CONDITIONAL:DEFAULT_VALUE'_FME_NO_OP_'BOOL_OP;OR;COMPOSITE_TEST;1;TEST lon_deg_tile22 ATTRIBUTE_IS_MISSING _FME_BLANK_STRING_'@Value(lon_deg_tile1)'FME_NUM_CONDITIONS2___
      SET_TO xtile22 = FME_CONDITIONAL:DEFAULT_VALUE'_FME_NO_OP_'BOOL_OP;OR;COMPOSITE_TEST;1;TEST xtile22 ATTRIBUTE_IS_MISSING _FME_BLANK_STRING_'@Value(xtile1)'FME_NUM_CONDITIONS2___
      SET_TO ytile22 = FME_CONDITIONAL:DEFAULT_VALUE'_FME_NO_OP_'BOOL_OP;OR;COMPOSITE_TEST;1;TEST ytile22 ATTRIBUTE_IS_MISSING _FME_BLANK_STRING_'@Value(ytile1)'FME_NUM_CONDITIONS2___
      SET_TO lat_deg_tile23 = FME_CONDITIONAL:DEFAULT_VALUE'_FME_NO_OP_'BOOL_OP;OR;COMPOSITE_TEST;1;TEST lat_deg_tile23 ATTRIBUTE_IS_MISSING _FME_BLANK_STRING_'@Value(lat_deg_tile1)'FME_NUM_CONDITIONS2___
      SET_TO lon_deg_tile23 = FME_CONDITIONAL:DEFAULT_VALUE'_FME_NO_OP_'BOOL_OP;OR;COMPOSITE_TEST;1;TEST lon_deg_tile23 ATTRIBUTE_IS_MISSING _FME_BLANK_STRING_'@Value(lon_deg_tile1)'FME_NUM_CONDITIONS2___
      SET_TO xtile23 = FME_CONDITIONAL:DEFAULT_VALUE'_FME_NO_OP_'BOOL_OP;OR;COMPOSITE_TEST;1;TEST xtile23 ATTRIBUTE_IS_MISSING _FME_BLANK_STRING_'@Value(xtile1)'FME_NUM_CONDITIONS2___
      SET_TO ytile23 = FME_CONDITIONAL:DEFAULT_VALUE'_FME_NO_OP_'BOOL_OP;OR;COMPOSITE_TEST;1;TEST ytile23 ATTRIBUTE_IS_MISSING _FME_BLANK_STRING_'@Value(ytile1)'FME_NUM_CONDITIONS2___
      SET_TO lat_deg_tile24 = FME_CONDITIONAL:DEFAULT_VALUE'_FME_NO_OP_'BOOL_OP;OR;COMPOSITE_TEST;1;TEST lat_deg_tile24 ATTRIBUTE_IS_MISSING _FME_BLANK_STRING_'@Value(lat_deg_tile1)'FME_NUM_CONDITIONS2___
      SET_TO lon_deg_tile24 = FME_CONDITIONAL:DEFAULT_VALUE'_FME_NO_OP_'BOOL_OP;OR;COMPOSITE_TEST;1;TEST lon_deg_tile24 ATTRIBUTE_IS_MISSING _FME_BLANK_STRING_'@Value(lon_deg_tile1)'FME_NUM_CONDITIONS2___
      SET_TO xtile24 = FME_CONDITIONAL:DEFAULT_VALUE'_FME_NO_OP_'BOOL_OP;OR;COMPOSITE_TEST;1;TEST xtile24 ATTRIBUTE_IS_MISSING _FME_BLANK_STRING_'@Value(xtile1)'FME_NUM_CONDITIONS2___
      SET_TO ytile24 = FME_CONDITIONAL:DEFAULT_VALUE'_FME_NO_OP_'BOOL_OP;OR;COMPOSITE_TEST;1;TEST ytile24 ATTRIBUTE_IS_MISSING _FME_BLANK_STRING_'@Value(ytile1)'FME_NUM_CONDITIONS2___
      SET_TO lat_deg_tile25 = FME_CONDITIONAL:DEFAULT_VALUE'_FME_NO_OP_'BOOL_OP;OR;COMPOSITE_TEST;1;TEST lat_deg_tile25 ATTRIBUTE_IS_MISSING _FME_BLANK_STRING_'@Value(lat_deg_tile1)'FME_NUM_CONDITIONS2___
      SET_TO lon_deg_tile25 = FME_CONDITIONAL:DEFAULT_VALUE'_FME_NO_OP_'BOOL_OP;OR;COMPOSITE_TEST;1;TEST lon_deg_tile25 ATTRIBUTE_IS_MISSING _FME_BLANK_STRING_'@Value(lon_deg_tile1)'FME_NUM_CONDITIONS2___
      SET_TO xtile25 = FME_CONDITIONAL:DEFAULT_VALUE'_FME_NO_OP_'BOOL_OP;OR;COMPOSITE_TEST;1;TEST xtile25 ATTRIBUTE_IS_MISSING _FME_BLANK_STRING_'@Value(xtile1)'FME_NUM_CONDITIONS2___
      SET_TO ytile25 = FME_CONDITIONAL:DEFAULT_VALUE'_FME_NO_OP_'BOOL_OP;OR;COMPOSITE_TEST;1;TEST ytile25 ATTRIBUTE_IS_MISSING _FME_BLANK_STRING_'@Value(ytile1)'FME_NUM_CONDITIONS2___
      SET_TO lat_deg_tile_b2 = FME_CONDITIONAL:DEFAULT_VALUE'_FME_NO_OP_'BOOL_OP;OR;COMPOSITE_TEST;1;TEST lat_deg_tile_b2 ATTRIBUTE_IS_MISSING _FME_BLANK_STRING_'@Value(lat_deg_tile_b1)'FME_NUM_CONDITIONS2___
      SET_TO lat_deg_tile_b3 = FME_CONDITIONAL:DEFAULT_VALUE'_FME_NO_OP_'BOOL_OP;OR;COMPOSITE_TEST;1;TEST lat_deg_tile_b3 ATTRIBUTE_IS_MISSING _FME_BLANK_STRING_'@Value(lat_deg_tile_b1)'FME_NUM_CONDITIONS2___
      SET_TO lat_deg_tile_b4 = FME_CONDITIONAL:DEFAULT_VALUE'_FME_NO_OP_'BOOL_OP;OR;COMPOSITE_TEST;1;TEST lat_deg_tile_b4 ATTRIBUTE_IS_MISSING _FME_BLANK_STRING_'@Value(lat_deg_tile_b1)'FME_NUM_CONDITIONS2___
      SET_TO lat_deg_tile_b5 = FME_CONDITIONAL:DEFAULT_VALUE'_FME_NO_OP_'BOOL_OP;OR;COMPOSITE_TEST;1;TEST lat_deg_tile_b5 ATTRIBUTE_IS_MISSING _FME_BLANK_STRING_'@Value(lat_deg_tile_b1)'FME_NUM_CONDITIONS2___
      SET_TO lat_deg_tile_b6 = FME_CONDITIONAL:DEFAULT_VALUE'_FME_NO_OP_'BOOL_OP;OR;COMPOSITE_TEST;1;TEST lat_deg_tile_b6 ATTRIBUTE_IS_MISSING _FME_BLANK_STRING_'@Value(lat_deg_tile_b1)'FME_NUM_CONDITIONS2___
      SET_TO lat_deg_tile_b7 = FME_CONDITIONAL:DEFAULT_VALUE'_FME_NO_OP_'BOOL_OP;OR;COMPOSITE_TEST;1;TEST lat_deg_tile_b7 ATTRIBUTE_IS_MISSING _FME_BLANK_STRING_'@Value(lat_deg_tile_b1)'FME_NUM_CONDITIONS2___
      SET_TO lat_deg_tile_b8 = FME_CONDITIONAL:DEFAULT_VALUE'_FME_NO_OP_'BOOL_OP;OR;COMPOSITE_TEST;1;TEST lat_deg_tile_b8 ATTRIBUTE_IS_MISSING _FME_BLANK_STRING_'@Value(lat_deg_tile_b1)'FME_NUM_CONDITIONS2___
      SET_TO lat_deg_tile_b9 = FME_CONDITIONAL:DEFAULT_VALUE'_FME_NO_OP_'BOOL_OP;OR;COMPOSITE_TEST;1;TEST lat_deg_tile_b9 ATTRIBUTE_IS_MISSING _FME_BLANK_STRING_'@Value(lat_deg_tile_b1)'FME_NUM_CONDITIONS2___
      SET_TO lat_deg_tile_b10 = FME_CONDITIONAL:DEFAULT_VALUE'_FME_NO_OP_'BOOL_OP;OR;COMPOSITE_TEST;1;TEST lat_deg_tile_b10 ATTRIBUTE_IS_MISSING _FME_BLANK_STRING_'@Value(lat_deg_tile_b1)'FME_NUM_CONDITIONS2___
      SET_TO lat_deg_tile_b11 = FME_CONDITIONAL:DEFAULT_VALUE'_FME_NO_OP_'BOOL_OP;OR;COMPOSITE_TEST;1;TEST lat_deg_tile_b11 ATTRIBUTE_IS_MISSING _FME_BLANK_STRING_'@Value(lat_deg_tile_b1)'FME_NUM_CONDITIONS2___
      SET_TO lat_deg_tile_b12 = FME_CONDITIONAL:DEFAULT_VALUE'_FME_NO_OP_'BOOL_OP;OR;COMPOSITE_TEST;1;TEST lat_deg_tile_b12 ATTRIBUTE_IS_MISSING _FME_BLANK_STRING_'@Value(lat_deg_tile_b1)'FME_NUM_CONDITIONS2___
      SET_TO lat_deg_tile_b13 = FME_CONDITIONAL:DEFAULT_VALUE'_FME_NO_OP_'BOOL_OP;OR;COMPOSITE_TEST;1;TEST lat_deg_tile_b13 ATTRIBUTE_IS_MISSING _FME_BLANK_STRING_'@Value(lat_deg_tile_b1)'FME_NUM_CONDITIONS2___
      SET_TO lat_deg_tile_b14 = FME_CONDITIONAL:DEFAULT_VALUE'_FME_NO_OP_'BOOL_OP;OR;COMPOSITE_TEST;1;TEST lat_deg_tile_b14 ATTRIBUTE_IS_MISSING _FME_BLANK_STRING_'@Value(lat_deg_tile_b1)'FME_NUM_CONDITIONS2___
      SET_TO lat_deg_tile_b15 = FME_CONDITIONAL:DEFAULT_VALUE'_FME_NO_OP_'BOOL_OP;OR;COMPOSITE_TEST;1;TEST lat_deg_tile_b15 ATTRIBUTE_IS_MISSING _FME_BLANK_STRING_'@Value(lat_deg_tile_b1)'FME_NUM_CONDITIONS2___
      SET_TO lat_deg_tile_b16 = FME_CONDITIONAL:DEFAULT_VALUE'_FME_NO_OP_'BOOL_OP;OR;COMPOSITE_TEST;1;TEST lat_deg_tile_b16 ATTRIBUTE_IS_MISSING _FME_BLANK_STRING_'@Value(lat_deg_tile_b1)'FME_NUM_CONDITIONS2___
      SET_TO lat_deg_tile_b17 = FME_CONDITIONAL:DEFAULT_VALUE'_FME_NO_OP_'BOOL_OP;OR;COMPOSITE_TEST;1;TEST lat_deg_tile_b17 ATTRIBUTE_IS_MISSING _FME_BLANK_STRING_'@Value(lat_deg_tile_b1)'FME_NUM_CONDITIONS2___
      SET_TO lat_deg_tile_b18 = FME_CONDITIONAL:DEFAULT_VALUE'_FME_NO_OP_'BOOL_OP;OR;COMPOSITE_TEST;1;TEST lat_deg_tile_b18 ATTRIBUTE_IS_MISSING _FME_BLANK_STRING_'@Value(lat_deg_tile_b1)'FME_NUM_CONDITIONS2___
      SET_TO lat_deg_tile_b19 = FME_CONDITIONAL:DEFAULT_VALUE'_FME_NO_OP_'BOOL_OP;OR;COMPOSITE_TEST;1;TEST lat_deg_tile_b19 ATTRIBUTE_IS_MISSING _FME_BLANK_STRING_'@Value(lat_deg_tile_b1)'FME_NUM_CONDITIONS2___
      SET_TO lat_deg_tile_b20 = FME_CONDITIONAL:DEFAULT_VALUE'_FME_NO_OP_'BOOL_OP;OR;COMPOSITE_TEST;1;TEST lat_deg_tile_b20 ATTRIBUTE_IS_MISSING _FME_BLANK_STRING_'@Value(lat_deg_tile_b1)'FME_NUM_CONDITIONS2___
      SET_TO lat_deg_tile_b21 = FME_CONDITIONAL:DEFAULT_VALUE'_FME_NO_OP_'BOOL_OP;OR;COMPOSITE_TEST;1;TEST lat_deg_tile_b21 ATTRIBUTE_IS_MISSING _FME_BLANK_STRING_'@Value(lat_deg_tile_b1)'FME_NUM_CONDITIONS2___
      SET_TO lat_deg_tile_b22 = FME_CONDITIONAL:DEFAULT_VALUE'_FME_NO_OP_'BOOL_OP;OR;COMPOSITE_TEST;1;TEST lat_deg_tile_b22 ATTRIBUTE_IS_MISSING _FME_BLANK_STRING_'@Value(lat_deg_tile_b1)'FME_NUM_CONDITIONS2___
      SET_TO lat_deg_tile_b23 = FME_CONDITIONAL:DEFAULT_VALUE'_FME_NO_OP_'BOOL_OP;OR;COMPOSITE_TEST;1;TEST lat_deg_tile_b23 ATTRIBUTE_IS_MISSING _FME_BLANK_STRING_'@Value(lat_deg_tile_b1)'FME_NUM_CONDITIONS2___
      SET_TO lat_deg_tile_b24 = FME_CONDITIONAL:DEFAULT_VALUE'_FME_NO_OP_'BOOL_OP;OR;COMPOSITE_TEST;1;TEST lat_deg_tile_b24 ATTRIBUTE_IS_MISSING _FME_BLANK_STRING_'@Value(lat_deg_tile_b1)'FME_NUM_CONDITIONS2___
      SET_TO lat_deg_tile_b25 = FME_CONDITIONAL:DEFAULT_VALUE'_FME_NO_OP_'BOOL_OP;OR;COMPOSITE_TEST;1;TEST lat_deg_tile_b25 ATTRIBUTE_IS_MISSING _FME_BLANK_STRING_'@Value(lat_deg_tile_b1)'FME_NUM_CONDITIONS2___
    -> FeatureJoiner_53 [LEFT]
FeatureJoiner_53
    ATTR_CONFLICT_RES = Use Left
    GEOMETRY_HANDLING = Use Left
    JOIN_KEYS = join join AUTO
    JOIN_MODE = Inner
    JOINED -> WorkspaceRunner_2
WorkspaceRunner_2
    BLOCKING = Yes
    WORKSPACE_FILE = $(FME_MF_DIR)Rasterextractorv3.fmw
    WORKSPACE_PARAMETERS = zoom,@Value(zoom),x_1,@Value(xtile1),x_2,@Value(xtile2),x_3,@Value(xtile3),x_4,@Value(xtile4),x_5,@Value(xtile5),x_6,@Value(xtile6),x_7,@Value(xtile7),x_8,@Value(xtile8),x_9,@Value(xtile9),x_10,@Value(xtile10),x_11,@Value(xtile11),x_12,@Value(xtile12),x_13,@Value(xtile13),x_14,@Value(xtile14),x_15,@Value(xtile15),x_16,@Value(xtile16),x_17,@Value(xtile17),x_18,@Value(xtile18),x_19,@Value(xtile19),x_20,@Value(xtile20),x_21,@Value(xtile21),x_22,@Value(xtile22),x_23,@Value(xtile23),x_24,@Value(xtile24),x_25,@Value(xtile25),y_1,@Value(ytile1),y_2,@Value(ytile2),y_3,@Value(ytile3),y_4,@Value(ytile4),y_5,@Value(ytile5),y_6,@Value(ytile6),y_7,@Value(ytile7),y_8,@Value(ytile8),y_9,@Value(ytile9),y_10,@Value(ytile10),y_11,@Value(ytile11),y_12,@Value(ytile12),y_13,@Value(ytile13),y_14,@Value(ytile14),y_15,@Value(ytile15),y_16,@Value(ytile16),y_17,@Value(ytile17),y_18,@Value(ytile18),y_19,@Value(ytile19),y_20,@Value(ytile20),y_21,@Value(ytile21),y_22,@Value(ytile22),y_23,@Value(ytile23),y_24,@Value(ytile24),y_25,@Value(ytile25),x_deg_1,@Value(lon_deg_tile1),x_deg_2,@Value(lon_deg_tile2),x_deg_3,@Value(lon_deg_tile3),x_deg_4,@Value(lon_deg_tile4),x_deg_5,@Value(lon_deg_tile5),x_deg_6,@Value(lon_deg_tile6),x_deg_7,@Value(lon_deg_tile7),x_deg_8,@Value(lon_deg_tile8),x_deg_9,@Value(lon_deg_tile9),x_deg_10,@Value(lon_deg_tile10),x_deg_11,@Value(lon_deg_tile11),x_deg_12,@Value(lon_deg_tile12),x_deg_13,@Value(lon_deg_tile13),x_deg_14,@Value(lon_deg_tile14),x_deg_15,@Value(lon_deg_tile15),x_deg_16,@Value(lon_deg_tile16),x_deg_17,@Value(lon_deg_tile17),x_deg_18,@Value(lon_deg_tile18),x_deg_19,@Value(lon_deg_tile19),x_deg_20,@Value(lon_deg_tile20),x_deg_21,@Value(lon_deg_tile21),x_deg_22,@Value(lon_deg_tile22),x_deg_23,@Value(lon_deg_tile23),x_deg_24,@Value(lon_deg_tile24),x_deg_25,@Value(lon_deg_tile25),y_deg_1,@Value(lat_deg_tile1),y_deg_2,@Value(lat_deg_tile2),y_deg_3,@Value(lat_deg_tile3),y_deg_4,@Value(lat_deg_tile4),y_deg_5,@Value(lat_deg_tile5),y_deg_6,@Value(lat_deg_tile6),y_deg_7,@Value(lat_deg_tile7),y_deg_8,@Value(lat_deg_tile8),y_deg_9,@Value(lat_deg_tile9),y_deg_10,@Value(lat_deg_tile10),y_deg_11,@Value(lat_deg_tile11),y_deg_12,@Value(lat_deg_tile12),y_deg_13,@Value(lat_deg_tile13),y_deg_14,@Value(lat_deg_tile14),y_deg_15,@Value(lat_deg_tile15),y_deg_16,@Value(lat_deg_tile16),y_deg_17,@Value(lat_deg_tile17),y_deg_18,@Value(lat_deg_tile18),y_deg_19,@Value(lat_deg_tile19),y_deg_20,@Value(lat_deg_tile20),y_deg_21,@Value(lat_deg_tile21),y_deg_22,@Value(lat_deg_tile22),y_deg_23,@Value(lat_deg_tile23),y_deg_24,@Value(lat_deg_tile24),y_deg_25,@Value(lat_deg_tile25),y_deg_b_1,@Value(lat_deg_tile_b1),y_deg_b_2,@Value(lat_deg_tile_b2),y_deg_b_3,@Value(lat_deg_tile_b3),y_deg_b_4,@Value(lat_deg_tile_b4),y_deg_b_5,@Value(lat_deg_tile_b5),y_deg_b_6,@Value(lat_deg_tile_b6),y_deg_b_7,@Value(lat_deg_tile_b7),y_deg_b_8,@Value(lat_deg_tile_b8),y_deg_b_9,@Value(lat_deg_tile_b9),y_deg_b_10,@Value(lat_deg_tile_b10),y_deg_b_11,@Value(lat_deg_tile_b11),y_deg_b_12,@Value(lat_deg_tile_b12),y_deg_b_13,@Value(lat_deg_tile_b13),y_deg_b_14,@Value(lat_deg_tile_b14),y_deg_b_15,@Value(lat_deg_tile_b15),y_deg_b_16,@Value(lat_deg_tile_b16),y_deg_b_17,@Value(lat_deg_tile_b17),y_deg_b_18,@Value(lat_deg_tile_b18),y_deg_b_19,@Value(lat_deg_tile_b19),y_deg_b_20,@Value(lat_deg_tile_b20),y_deg_b_21,@Value(lat_deg_tile_b21),y_deg_b_22,@Value(lat_deg_tile_b22),y_deg_b_23,@Value(lat_deg_tile_b23),y_deg_b_24,@Value(lat_deg_tile_b24),y_deg_b_25,@Value(lat_deg_tile_b25),min_lon,@Value(min_x),min_lat,@Value(min_y),max_lon,@Value(max_x),max_lat,@Value(max_y),DestDataset_JPEG,$(FME_MF_DIR_USERTYPED)output_@Value(ISO_merge)\05_PDF_export,DestDataset_PNGRASTER,$(FME_MF_DIR_USERTYPED)output_@Value(ISO_merge)\05_PDF_export,BASEMAPE,$(BaseMap),BASEMAPE_ext,.png,ISO_code,@Value(ISO_merge),DestDataset_JPEG2000_3,$(FME_MF_DIR_USERTYPED)output_@Value(ISO_merge)\05_PDF_export\subtiles,DestDataset_PNGRASTER_3,$(FME_MF_DIR_USERTYPED)output_@Value(ISO_merge)\05_PDF_export\subtiles,DestDataset_JPEG_4,$(FME_MF_DIR_USERTYPED)output_@Value(ISO_merge)\05_PDF_export\subtiles,DestDataset_JPEG2000,$(FME_MF_DIR_USERTYPED)output_@Value(ISO_merge)\05_PDF_export
    SUCCEEDED -> Cloner_5
Cloner_5
    COPIES = 13
    COPYATT = _copynum
    COPY -> AttributeManager_125
AttributeManager_125
    ATTR_TABLE:
      REMOVE lat_deg_tile1
      REMOVE lon_deg_tile1
      REMOVE xtile1
      REMOVE ytile1
      REMOVE join
      REMOVE n
      REMOVE lat_deg_tile2
      REMOVE lon_deg_tile2
      REMOVE xtile2
      REMOVE ytile2
      REMOVE lat_deg_tile3
      REMOVE lon_deg_tile3
      REMOVE xtile3
      REMOVE ytile3
      REMOVE lat_deg_tile4
      REMOVE lon_deg_tile4
      REMOVE xtile4
      REMOVE ytile4
      REMOVE lat_deg_tile5
      REMOVE lon_deg_tile5
      REMOVE xtile5
      REMOVE ytile5
      REMOVE lat_deg_tile6
      REMOVE lon_deg_tile6
      REMOVE xtile6
      REMOVE ytile6
      REMOVE lat_deg_tile7
      REMOVE lon_deg_tile7
      REMOVE xtile7
      REMOVE ytile7
      REMOVE lat_deg_tile8
      REMOVE lon_deg_tile8
      REMOVE xtile8
      REMOVE ytile8
      REMOVE lat_deg_tile9
      REMOVE lon_deg_tile9
      REMOVE xtile9
      REMOVE ytile9
      REMOVE lat_deg_tile10
      REMOVE lon_deg_tile10
      REMOVE xtile10
      REMOVE ytile10
      REMOVE lat_deg_tile11
      REMOVE lon_deg_tile11
      REMOVE xtile11
      REMOVE ytile11
      REMOVE lat_deg_tile12
      REMOVE lon_deg_tile12
      REMOVE xtile12
      REMOVE ytile12
      REMOVE lat_deg_tile13
      REMOVE lon_deg_tile13
      REMOVE xtile13
      REMOVE ytile13
      REMOVE lat_deg_tile14
      REMOVE lon_deg_tile14
      REMOVE xtile14
      REMOVE ytile14
      REMOVE lat_deg_tile15
      REMOVE lon_deg_tile15
      REMOVE xtile15
      REMOVE ytile15
      REMOVE lat_deg_tile16
      REMOVE lon_deg_tile16
      REMOVE xtile16
      REMOVE ytile16
      REMOVE lat_deg_tile17
      REMOVE lon_deg_tile17
      REMOVE xtile17
      REMOVE ytile17
      REMOVE lat_deg_tile18
      REMOVE lon_deg_tile18
      REMOVE xtile18
      REMOVE ytile18
      REMOVE lat_deg_tile19
      REMOVE lon_deg_tile19
      REMOVE xtile19
      REMOVE ytile19
      REMOVE lat_deg_tile20
      REMOVE lon_deg_tile20
      REMOVE xtile20
      REMOVE ytile20
      REMOVE lat_deg_tile21
      REMOVE lon_deg_tile21
      REMOVE xtile21
      REMOVE ytile21
      REMOVE lat_deg_tile22
      REMOVE lon_deg_tile22
      REMOVE xtile22
      REMOVE ytile22
      REMOVE lat_deg_tile23
      REMOVE lon_deg_tile23
      REMOVE xtile23
      REMOVE ytile23
      REMOVE lat_deg_tile24
      REMOVE lon_deg_tile24
      REMOVE xtile24
      REMOVE ytile24
      REMOVE lat_deg_tile25
      REMOVE lon_deg_tile25
      REMOVE xtile25
      REMOVE ytile25
      REMOVE lat_deg_tile_b1
      REMOVE lat_deg_tile_b2
      REMOVE lat_deg_tile_b3
      REMOVE lat_deg_tile_b4
      REMOVE lat_deg_tile_b5
      REMOVE lat_deg_tile_b6
      REMOVE lat_deg_tile_b7
      REMOVE lat_deg_tile_b8
      REMOVE lat_deg_tile_b9
      REMOVE lat_deg_tile_b10
      REMOVE lat_deg_tile_b11
      REMOVE lat_deg_tile_b12
      REMOVE lat_deg_tile_b13
      REMOVE lat_deg_tile_b14
      REMOVE lat_deg_tile_b15
      REMOVE lat_deg_tile_b16
      REMOVE lat_deg_tile_b17
      REMOVE lat_deg_tile_b18
      REMOVE lat_deg_tile_b19
      REMOVE lat_deg_tile_b20
      REMOVE lat_deg_tile_b21
      REMOVE lat_deg_tile_b22
      REMOVE lat_deg_tile_b23
      REMOVE lat_deg_tile_b24
      REMOVE lat_deg_tile_b25
      REMOVE ISO3
      SET_TO choice_PDF = $(Features_PDF)
      SET_TO feature_num = @WordCount(@Value(choice_PDF))
      SET_TO width_BB_km = @Evaluate(@Value(_length.max)*111*@cos(@pi()*@Value(max_y)*(1/180)))
      SET_TO date_totday = @DateTimeFormat(@DateTimeNow(),%Y%m%d)
      SET_TO pdf_name = FME_CONDITIONAL:DEFAULT_VALUE'BoudingBox_PDF_export_tile_@Value(_copynum)'BOOL_OP;OR;COMPOSITE_TEST;1;TEST @Value(_copynum) = 0'BoundingBox_PDF_export_full'FME_NUM_CONDITIONS2___
      SET_TO source_jpeg = FME_CONDITIONAL:DEFAULT_VALUE'$(FME_MF_DIR_USERTYPED)output_@Value(ISO_merge)\05_PDF_export\subtiles\subbasemap_@Value(ISO_merge)_@sub(@Value(_copynum),1).jp2'BOOL_OP;OR;COMPOSITE_TEST;1;TEST @Value(_copynum) = 0'$(FME_MF_DIR_USERTYPED)output_@Value(ISO_merge)\05_PDF_export\basemap_@Value(ISO_merge).jp2'BOOL_OP;OR;COMPOSITE_TEST;1;TEST @Value(_copynum) = 1'$(FME_MF_DIR_USERTYPED)output_@Value(ISO_merge)\05_PDF_export\subtiles\subbasemap_@Value(ISO_merge).jp2'FME_NUM_CONDITIONS3___
    -> ExportPDF
ExportPDF: WorkspaceRunner
    BLOCKING = Yes
    WORKSPACE_FILE = $(FME_MF_DIR)GeospatialPDF_v4.fmw
    WORKSPACE_PARAMETERS = SourceDataset_JPEG2000,@Value(source_jpeg),Zoom,@Value(zoom),FILE_name,@Value(pdf_name),DestDataset_PDF2D,$(FME_MF_DIR_USERTYPED)output_@Value(ISO_merge)\05_PDF_export\@Value(pdf_name).pdf,Tile_num,@Value(_copynum),SQUARE_SIZE_KM,@Value(width_BB_km),Features_to_print,@Value(choice_PDF),Number_of_features,@Value(feature_num),Layer_feature,$(FME_MF_DIR_USERTYPED)output,DATE,@Value(date_totday),ISO,@Value(ISO_merge),SourceDataset_PDF2D,$(FME_MF_DIR_USERTYPED)PDF_legend.pdf,ISO3,@Value(ISO_merge),GEOM,@Value(min_x) @Value(min_y) @Value(max_x) @Value(max_y)
AttributeManager_106
    ATTR_TABLE:
      REMOVE _count00
      REMOVE _count2
      REMOVE _count99

Bookmark: Special char
StringReplacer_3
    CASE = NO
    FIND_TEXT = \u00e0
    NO_MATCH = _FME_NO_OP_
    REGEXP = NO
    REPLACE_TEXT = à
    SRC_ATTRS = _json_response
    -> StringReplacer_4
StringReplacer_4
    CASE = NO
    FIND_TEXT = \u00e8
    NO_MATCH = _FME_NO_OP_
    REGEXP = NO
    REPLACE_TEXT = è
    SRC_ATTRS = _json_response
    -> StringReplacer_5
StringReplacer_5
    CASE = NO
    FIND_TEXT = \u00e9
    NO_MATCH = _FME_NO_OP_
    REGEXP = NO
    REPLACE_TEXT = é
    SRC_ATTRS = _json_response
    -> StringReplacer_6
StringReplacer_6
    CASE = NO
    FIND_TEXT = \u00e7
    NO_MATCH = _FME_NO_OP_
    REGEXP = NO
    REPLACE_TEXT = ç
    SRC_ATTRS = _json_response
    -> StringReplacer_7
StringReplacer_7
    CASE = NO
    FIND_TEXT = \u00e2
    NO_MATCH = _FME_NO_OP_
    REGEXP = NO
    REPLACE_TEXT = â
    SRC_ATTRS = _json_response
    -> StringReplacer_8
StringReplacer_8
    CASE = NO
    FIND_TEXT = \u00f4
    NO_MATCH = _FME_NO_OP_
    REGEXP = NO
    REPLACE_TEXT = ô
    SRC_ATTRS = _json_response
    -> StringReplacer

Bookmark: County
StringSearcher_6
    CASE = no
    MATCHED_RESULT_ATTR = county
    REGEXP = county": .{0,20}
    STRING_TO_SEARCH = @Value(_json_response)
    MATCHED -> AttributeManager_15
    NOT_MATCHED -> AttributeManager_14
AttributeManager_14
    ATTR_TABLE = SET_TO county = null
    -> FeatureJoiner_4 [LEFT]
AttributeManager_15
    ATTR_TABLE:
      SET_TO county = @ReplaceString(@Value(county),county": ",,caseSensitive=TRUE)
      SET_TO county1 = @GetWord(@Value(county),0)
      SET_TO county2 = @GetWord(@Value(county),1)
      SET_TO county3 = @GetWord(@Value(county),2)
    -> TestFilter_8
TestFilter_8
    DEFAULT_VALUE = merge2andelete1
    TEST_LIST = "BOOL_OP,OR,COMPOSITE_TEST,""""""1"""""",TEST_CLAUSE,CASE_INSENSITIVE_TEST @Value(county1) ENDS_WITH },",delete2,"BOOL_OP,OR,COMPOSITE_TEST,""""""1"""""",TEST_CLAUSE,CASE_INSENSITIVE_TEST @Value(county2) BEGINS_WITH "",delete1,"BOOL_OP,OR,COMPOSITE_TEST,""""""1"""""",TEST_CLAUSE,CASE_INSENSITIVE_TEST @Value(county2) ENDS_WITH },",mergeanddelete2,"BOOL_OP,OR,COMPOSITE_TEST,""""""1"""""",TEST_CLAUSE,CASE_INSENSITIVE_TEST @Value(county3) BEGINS_WITH "",mergeanddelete1,"BOOL_OP,OR,COMPOSITE_TEST,""""""1"""""",TEST_CLAUSE,CASE_INSENSITIVE_TEST @Value(county3) ENDS_WITH },",merge2anddelete2
    delete2 -> SubstringExtractor_16
    delete1 -> SubstringExtractor_17
    mergeanddelete2 -> AttributeManager_29
    mergeanddelete1 -> AttributeManager_30
    merge2anddelete2 -> AttributeManager_31
    merge2andelete1 -> AttributeManager_32
SubstringExtractor_16
    END = -4
    RESULT_ATTR = county
    SRC_STRING = @Value(county1)
    START = 0
    -> AttributeManager_33
SubstringExtractor_17
    END = -3
    RESULT_ATTR = county
    SRC_STRING = @Value(county1)
    START = 0
    -> AttributeManager_33
AttributeManager_29
    ATTR_TABLE = SET_TO county = @Value(county1) @Value(county2)
    USER_EXPOSED_ATTRIBUTES = county,county1,county2
    -> SubstringExtractor_18
SubstringExtractor_18
    END = -4
    RESULT_ATTR = state
    SRC_STRING = @Value(county)
    START = 0
    -> AttributeManager_33
AttributeManager_30
    ATTR_TABLE = SET_TO county = @Value(county1) @Value(county2)
    USER_EXPOSED_ATTRIBUTES = county,county1,county2,county3
    -> SubstringExtractor_19
SubstringExtractor_19
    END = -3
    RESULT_ATTR = county
    SRC_STRING = @Value(county)
    START = 0
    -> AttributeManager_33
AttributeManager_31
    ATTR_TABLE = SET_TO county = @Value(county1) @Value(county2) @Value(county3)
    USER_EXPOSED_ATTRIBUTES = county
    -> SubstringExtractor_20
SubstringExtractor_20
    END = -5
    RESULT_ATTR = county
    SRC_STRING = @Value(county)
    START = 0
    -> AttributeManager_33
AttributeManager_32
    ATTR_TABLE = SET_TO county = @Value(county1) @Value(county2) @Value(county3)
    USER_EXPOSED_ATTRIBUTES = county,state2,coun,state3
    -> SubstringExtractor_21
SubstringExtractor_21
    END = -4
    RESULT_ATTR = county
    SRC_STRING = @Value(county)
    START = 0
    -> AttributeManager_33
AttributeManager_33
    ATTR_TABLE:
      REMOVE state
      REMOVE county1
      REMOVE county2
      REMOVE county3
    USER_EXPOSED_ATTRIBUTES = state1,state2,state3
    -> FeatureJoiner_4 [LEFT]

Bookmark: Region
StringSearcher_5
    CASE = no
    MATCHED_RESULT_ATTR = region
    REGEXP = region": .{0,40}
    STRING_TO_SEARCH = @Value(_json_response)
    MATCHED -> AttributeManager_13
    NOT_MATCHED -> AttributeManager_16
AttributeManager_16
    ATTR_TABLE = SET_TO region = null
    -> FeatureJoiner_4 [RIGHT]
AttributeManager_13
    ATTR_TABLE:
      SET_TO region = @ReplaceString(@Value(region),region": ",,caseSensitive=TRUE)
      SET_TO region1 = @GetWord(@Value(region),0)
      SET_TO region2 = @GetWord(@Value(region),1)
      SET_TO region3 = @GetWord(@Value(region),2)
      SET_TO region4 = @GetWord(@Value(region),3)
    -> TestFilter_4
TestFilter_4
    DEFAULT_VALUE = merge3andelete1
    TEST_LIST = "BOOL_OP,OR,COMPOSITE_TEST,""""""1"""""",TEST_CLAUSE,CASE_INSENSITIVE_TEST @Value(region1) ENDS_WITH },",delete2,"BOOL_OP,OR,COMPOSITE_TEST,""""""1"""""",TEST_CLAUSE,CASE_INSENSITIVE_TEST @Value(region2) BEGINS_WITH "",delete1,"BOOL_OP,OR,COMPOSITE_TEST,""""""1"""""",TEST_CLAUSE,CASE_INSENSITIVE_TEST @Value(region2) ENDS_WITH },",mergeanddelete2,"BOOL_OP,OR,COMPOSITE_TEST,""""""1"""""",TEST_CLAUSE,CASE_INSENSITIVE_TEST @Value(region3) BEGINS_WITH "",mergeanddelete1,"BOOL_OP,OR,COMPOSITE_TEST,""""""1"""""",TEST_CLAUSE,CASE_INSENSITIVE_TEST @Value(region3) ENDS_WITH },",merge2anddelete2,"BOOL_OP,OR,COMPOSITE_TEST,""""""1"""""",TEST_CLAUSE,CASE_INSENSITIVE_TEST @Value(region4) BEGINS_WITH "",merge2andelete1,"BOOL_OP,OR,COMPOSITE_TEST,""""""1"""""",TEST_CLAUSE,CASE_INSENSITIVE_TEST @Value(region4) ENDS_WITH },",merge3andelete2
    delete2 -> SubstringExtractor_8
    delete1 -> SubstringExtractor_9
    mergeanddelete2 -> AttributeManager_22
    mergeanddelete1 -> AttributeManager_23
    merge2anddelete2 -> AttributeManager_24
    merge2andelete1 -> AttributeManager_25
    merge3andelete2 -> AttributeManager_27
    merge3andelete1 -> AttributeManager_28
SubstringExtractor_8
    END = -4
    RESULT_ATTR = region
    SRC_STRING = @Value(region1)
    START = 0
    -> AttributeManager_26
SubstringExtractor_9
    END = -3
    RESULT_ATTR = region
    SRC_STRING = @Value(region1)
    START = 0
    -> AttributeManager_26
AttributeManager_22
    ATTR_TABLE = SET_TO region = @Value(region1) @Value(region2)
    USER_EXPOSED_ATTRIBUTES = region,region1,region2
    -> SubstringExtractor_10
SubstringExtractor_10
    END = -4
    RESULT_ATTR = region
    SRC_STRING = @Value(region)
    START = 0
    -> AttributeManager_26
AttributeManager_23
    ATTR_TABLE = SET_TO region = @Value(region1) @Value(region2)
    USER_EXPOSED_ATTRIBUTES = region,region1,region2,region3
    -> SubstringExtractor_11
SubstringExtractor_11
    END = -3
    RESULT_ATTR = region
    SRC_STRING = @Value(region)
    START = 0
    -> AttributeManager_26
AttributeManager_24
    ATTR_TABLE = SET_TO region = @Value(region1) @Value(region2) @Value(region3)
    USER_EXPOSED_ATTRIBUTES = region,region1,region2,region3
    -> SubstringExtractor_12
SubstringExtractor_12
    END = -5
    RESULT_ATTR = region
    SRC_STRING = @Value(region)
    START = 0
    -> AttributeManager_26
AttributeManager_25
    ATTR_TABLE = SET_TO region = @Value(region1) @Value(region2) @Value(region3)
    USER_EXPOSED_ATTRIBUTES = region,region1,region2,region3
    -> SubstringExtractor_13
SubstringExtractor_13
    END = -4
    RESULT_ATTR = region
    SRC_STRING = @Value(region)
    START = 0
    -> AttributeManager_26
AttributeManager_27
    ATTR_TABLE = SET_TO region = @Value(region1) @Value(region2) @Value(region3) @Value(region4)
    USER_EXPOSED_ATTRIBUTES = region,region1,region2,region3
    -> SubstringExtractor_14
SubstringExtractor_14
    END = -5
    RESULT_ATTR = region
    SRC_STRING = @Value(region)
    START = 0
    -> AttributeManager_26
AttributeManager_28
    ATTR_TABLE = SET_TO region = @Value(region1) @Value(region2) @Value(region3) @Value(region4)
    USER_EXPOSED_ATTRIBUTES = region,region1,region2,region3
    -> SubstringExtractor_15
SubstringExtractor_15
    END = -4
    RESULT_ATTR = region
    SRC_STRING = @Value(region)
    START = 0
    -> AttributeManager_26
AttributeManager_26
    ATTR_TABLE:
      REMOVE region1
      REMOVE region2
      REMOVE region3
      REMOVE region1
      REMOVE region2
      REMOVE region3
      REMOVE region4
    USER_EXPOSED_ATTRIBUTES = region1,region2,region3
    -> FeatureJoiner_4 [RIGHT]

Bookmark: Country
StringSearcher
    CASE = no
    MATCHED_RESULT_ATTR = country
    REGEXP = country_code": ...
    STRING_TO_SEARCH = @Value(_json_response)
    MATCHED -> AttributeManager_3
    NOT_MATCHED -> AttributeManager_35
AttributeManager_35
    ATTR_TABLE = SET_TO country = null
    -> FeatureJoiner_5 [RIGHT]
AttributeManager_3
    ATTR_TABLE = SET_TO country = @ReplaceString(@Value(country),country_code": ",,caseSensitive=TRUE)
    -> AttributeManager_9
AttributeManager_9
    ATTR_TABLE = SET_TO country = @ReplaceString(@Value(country),country_code": ",,caseSensitive=TRUE)
    -> FeatureJoiner_5 [RIGHT]

Bookmark: States
StringSearcher_2
    CASE = no
    MATCHED_RESULT_ATTR = state
    REGEXP = state": ".{0,40}
    STRING_TO_SEARCH = @Value(_json_response)
    MATCHED -> AttributeManager_6
    NOT_MATCHED -> AttributeManager_34
AttributeManager_34
    ATTR_TABLE = SET_TO state = null
    -> FeatureJoiner_3 [RIGHT]
AttributeManager_6
    ATTR_TABLE:
      SET_TO state = @ReplaceString(@Value(state),state": ",,caseSensitive=TRUE)
      SET_TO state1 = @GetWord(@Value(state),0)
      SET_TO state2 = @GetWord(@Value(state),1)
      SET_TO state3 = @GetWord(@Value(state),2)
    -> TestFilter_7
TestFilter_7
    DEFAULT_VALUE = merge2andelete1
    TEST_LIST = "BOOL_OP,OR,COMPOSITE_TEST,""""""1"""""",TEST_CLAUSE,CASE_INSENSITIVE_TEST @Value(state1) ENDS_WITH },",delete2,"BOOL_OP,OR,COMPOSITE_TEST,""""""1"""""",TEST_CLAUSE,CASE_INSENSITIVE_TEST @Value(state2) BEGINS_WITH "",delete1,"BOOL_OP,OR,COMPOSITE_TEST,""""""1"""""",TEST_CLAUSE,CASE_INSENSITIVE_TEST @Value(state2) ENDS_WITH },",mergeanddelete2,"BOOL_OP,OR,COMPOSITE_TEST,""""""1"""""",TEST_CLAUSE,CASE_INSENSITIVE_TEST @Value(state3) BEGINS_WITH "",mergeanddelete1,"BOOL_OP,OR,COMPOSITE_TEST,""""""1"""""",TEST_CLAUSE,CASE_INSENSITIVE_TEST @Value(state3) ENDS_WITH },",merge2anddelete2
    delete2 -> SubstringExtractor_2
    delete1 -> SubstringExtractor_3
    mergeanddelete2 -> AttributeManager_17
    mergeanddelete1 -> AttributeManager_18
    merge2anddelete2 -> AttributeManager_19
    merge2andelete1 -> AttributeManager_20
SubstringExtractor_2
    END = -4
    RESULT_ATTR = state
    SRC_STRING = @Value(state1)
    START = 0
    -> AttributeManager_21
SubstringExtractor_3
    END = -3
    RESULT_ATTR = state
    SRC_STRING = @Value(state1)
    START = 0
    -> AttributeManager_21
AttributeManager_17
    ATTR_TABLE = SET_TO state = @Value(state1) @Value(state2)
    -> SubstringExtractor_4
SubstringExtractor_4
    END = -4
    RESULT_ATTR = state
    SRC_STRING = @Value(state)
    START = 0
    -> AttributeManager_21
AttributeManager_18
    ATTR_TABLE = SET_TO state = @Value(state1) @Value(state2)
    -> SubstringExtractor_5
SubstringExtractor_5
    END = -3
    RESULT_ATTR = state
    SRC_STRING = @Value(state)
    START = 0
    -> AttributeManager_21
AttributeManager_19
    ATTR_TABLE = SET_TO state = @Value(state1) @Value(state2) @Value(state3)
    -> SubstringExtractor_6
SubstringExtractor_6
    END = -5
    RESULT_ATTR = state
    SRC_STRING = @Value(state)
    START = 0
    -> AttributeManager_21
AttributeManager_20
    ATTR_TABLE = SET_TO state = @Value(state1) @Value(state2) @Value(state3)
    -> SubstringExtractor_7
SubstringExtractor_7
    END = -4
    RESULT_ATTR = state
    SRC_STRING = @Value(state)
    START = 0
    -> AttributeManager_21
AttributeManager_21
    ATTR_TABLE:
      REMOVE state1
      REMOVE state2
      REMOVE state3
    -> FeatureJoiner_3 [RIGHT]

Bookmark: URL managment
AttributeManager_74
    ATTR_TABLE = SET_TO url = https://data.worldpop.org/GIS/Population/Global_2000_2020/2020/@Value(ISO3)/@LowerCase(@Value(ISO3))_ppp_2020.tif
    -> Counter_2
Counter_2
    CNT_ATTR = _count
    DOMAIN = counter
    SCOPE = Global
    START = 0
    -> StatisticsCalculator_3
StatisticsCalculator_3
    CALCULATION_MODE = NUMERIC
    FEAT_STATS = _count,NUMERIC_MODE,,MAX,,,,,,,,,,,
    COMPLETE -> TestFilter_14
TestFilter_14
    DEFAULT_VALUE = <UNFILTERED>
    TEST_LIST = "BOOL_OP,OR,COMPOSITE_TEST,""""""1"""""",TEST_CLAUSE,TEST @Value(_count) = 0",url0,"BOOL_OP,OR,COMPOSITE_TEST,""""""1"""""",TEST_CLAUSE,TEST @Value(_count) = 1",url1,"BOOL_OP,OR,COMPOSITE_TEST,""""""1"""""",TEST_CLAUSE,TEST @Value(_count) = 2",url2,"BOOL_OP,OR,COMPOSITE_TEST,""""""1"""""",TEST_CLAUSE,TEST @Value(_count) = 3",url3,"BOOL_OP,OR,COMPOSITE_TEST,""""""1"""""",TEST_CLAUSE,TEST @Value(_count) = 4",url4,"BOOL_OP,OR,COMPOSITE_TEST,""""""1"""""",TEST_CLAUSE,TEST @Value(_count) = 5",url5,"BOOL_OP,OR,COMPOSITE_TEST,""""""1"""""",TEST_CLAUSE,TEST @Value(_count) = 6",url6,"BOOL_OP,OR,COMPOSITE_TEST,""""""1"""""",TEST_CLAUSE,TEST @Value(_count) = 7",url7
    url0 -> AttributeManager_59
    url1 -> AttributeManager_60
    url2 -> AttributeManager_61
    url3 -> AttributeManager_62
    url4 -> AttributeManager_63
    url5 -> AttributeManager_64
    url6 -> AttributeManager_65
    url7 -> AttributeManager_66
AttributeManager_66
    ATTR_TABLE = RENAME_SET_VALUE url > url8
    -> FeatureJoiner_18 [RIGHT]
AttributeManager_65
    ATTR_TABLE = RENAME_SET_VALUE url > url7
    -> FeatureJoiner_17 [RIGHT]
AttributeManager_64
    ATTR_TABLE = RENAME_SET_VALUE url > url6
    -> FeatureJoiner_16 [RIGHT]
AttributeManager_63
    ATTR_TABLE = RENAME_SET_VALUE url > url5
    -> FeatureJoiner_15 [RIGHT]
AttributeManager_62
    ATTR_TABLE = RENAME_SET_VALUE url > url4
    -> FeatureJoiner_14 [RIGHT]
AttributeManager_61
    ATTR_TABLE = RENAME_SET_VALUE url > url3
    -> FeatureJoiner_13 [RIGHT]
AttributeManager_59
    ATTR_TABLE = RENAME_SET_VALUE url > url1
    -> FeatureJoiner_12 [LEFT]
AttributeManager_60
    ATTR_TABLE = RENAME_SET_VALUE url > url2
    -> FeatureJoiner_12 [RIGHT]
FeatureJoiner_12
    ATTR_CONFLICT_RES = Use Left
    GEOMETRY_HANDLING = Use Left
    JOIN_KEYS = max_x max_x AUTO
    JOIN_MODE = Inner
    JOINED -> FeatureJoiner_13 [LEFT]
    UNJOINED_LEFT -> AttributeManager_69
AttributeManager_69
    ATTR_TABLE:
      SET_TO url3 = @Value(url1)
      SET_TO url4 = @Value(url1)
      SET_TO url5 = @Value(url1)
      SET_TO url6 = @Value(url1)
      SET_TO url7 = @Value(url1)
      SET_TO url8 = @Value(url1)
      SET_TO url2 = @Value(url1)
    -> PopDensity100m
FeatureJoiner_13
    ATTR_CONFLICT_RES = Use Left
    GEOMETRY_HANDLING = Use Left
    JOIN_KEYS = max_x max_x AUTO
    JOIN_MODE = Inner
    JOINED -> FeatureJoiner_14 [LEFT]
    UNJOINED_LEFT -> AttributeManager_68
AttributeManager_68
    ATTR_TABLE:
      SET_TO url3 = @Value(url1)
      SET_TO url4 = @Value(url1)
      SET_TO url5 = @Value(url1)
      SET_TO url6 = @Value(url1)
      SET_TO url7 = @Value(url1)
      SET_TO url8 = @Value(url1)
    -> PopDensity100m
FeatureJoiner_14
    ATTR_CONFLICT_RES = Use Left
    GEOMETRY_HANDLING = Use Left
    JOIN_KEYS = max_x max_x AUTO
    JOIN_MODE = Inner
    JOINED -> FeatureJoiner_15 [LEFT]
    UNJOINED_LEFT -> AttributeManager_67
AttributeManager_67
    ATTR_TABLE:
      SET_TO url4 = @Value(url1)
      SET_TO url5 = @Value(url1)
      SET_TO url6 = @Value(url1)
      SET_TO url7 = @Value(url1)
      SET_TO url8 = @Value(url1)
    -> PopDensity100m
FeatureJoiner_15
    ATTR_CONFLICT_RES = Use Left
    GEOMETRY_HANDLING = Use Left
    JOIN_KEYS = max_x max_x AUTO
    JOIN_MODE = Inner
    JOINED -> FeatureJoiner_16 [LEFT]
    UNJOINED_LEFT -> AttributeManager_70
AttributeManager_70
    ATTR_TABLE:
      SET_TO url5 = @Value(url1)
      SET_TO url6 = @Value(url1)
      SET_TO url7 = @Value(url1)
      SET_TO url8 = @Value(url1)
    -> PopDensity100m
FeatureJoiner_16
    ATTR_CONFLICT_RES = Use Left
    GEOMETRY_HANDLING = Use Left
    JOIN_KEYS = max_x max_x AUTO
    JOIN_MODE = Inner
    JOINED -> FeatureJoiner_17 [LEFT]
    UNJOINED_LEFT -> AttributeManager_71
AttributeManager_71
    ATTR_TABLE:
      SET_TO url6 = @Value(url1)
      SET_TO url7 = @Value(url1)
      SET_TO url8 = @Value(url1)
    -> PopDensity100m
FeatureJoiner_17
    ATTR_CONFLICT_RES = Use Left
    GEOMETRY_HANDLING = Use Left
    JOIN_KEYS = max_x max_x AUTO
    JOIN_MODE = Inner
    JOINED -> FeatureJoiner_18 [LEFT]
    UNJOINED_LEFT -> AttributeManager_72
AttributeManager_72
    ATTR_TABLE:
      SET_TO url7 = @Value(url1)
      SET_TO url8 = @Value(url1)
    -> PopDensity100m
FeatureJoiner_18
    ATTR_CONFLICT_RES = Use Left
    GEOMETRY_HANDLING = Use Left
    JOIN_KEYS = max_x max_x AUTO
    JOIN_MODE = Inner
    UNJOINED_LEFT -> AttributeManager_73
AttributeManager_73
    ATTR_TABLE = SET_TO url8 = @Value(url1)
    -> PopDensity100m

Bookmark: Table Weather
JSONFragmenter_2
    EXPLODE_FORMAT = JSON
    EXTRACT_ATTR = No
    JSON_ATTR = _response_body
    JSON_QUERY = json[*]
    READ_FROM_FILE = NO
    REJECT_EMPTY_LISTS = YES
    FRAGMENTS -> JSONFragmenter_3
    <REJECTED> -> Logger
JSONFragmenter_3
    EXPLODE_FORMAT = JSON
    EXTRACT_ATTR = No
    JSON_ATTR = _response_body
    JSON_QUERY = json[*]
    READ_FROM_FILE = NO
    REJECT_EMPTY_LISTS = YES
    FRAGMENTS -> JSONFragmenter_4
    FRAGMENTS -> TestFilter_18
    FRAGMENTS -> TestFilter_21
    <REJECTED> -> Logger_2
JSONFragmenter_4
    EXPLODE_FORMAT = JSON
    EXTRACT_ATTR = No
    JSON_ATTR = _response_body
    JSON_QUERY = json[*]
    READ_FROM_FILE = NO
    REJECT_EMPTY_LISTS = YES
    FRAGMENTS -> JSONFragmenter_5
    <REJECTED> -> TestFilter_16
JSONFragmenter_5
    EXPLODE_FORMAT = JSON
    EXTRACT_ATTR = No
    JSON_ATTR = _response_body
    JSON_QUERY = json[*]
    READ_FROM_FILE = NO
    REJECT_EMPTY_LISTS = YES
    <REJECTED> -> TestFilter_17
TestFilter_17
    DEFAULT_VALUE = <UNFILTERED>
    TEST_LIST = "BOOL_OP,OR,COMPOSITE_TEST,""""""1"""""",TEST_CLAUSE,TEST @Value(json_index) = 3h",rain,"BOOL_OP,OR,COMPOSITE_TEST,""""""1"""""",TEST_CLAUSE,TEST @Value(json_index) = all",cloudiness,"BOOL_OP,OR,COMPOSITE_TEST,""""""1"""""",TEST_CLAUSE,TEST @Value(json_index) = deg",wind_dir,"BOOL_OP,OR,COMPOSITE_TEST,""""""1"""""",TEST_CLAUSE,TEST @Value(json_index) = feels_like",temp_fl,"BOOL_OP,OR,COMPOSITE_TEST,""""""1"""""",TEST_CLAUSE,TEST @Value(json_index) = grnd_level",pressure_gl,"BOOL_OP,OR,COMPOSITE_TEST,""""""1"""""",TEST_CLAUSE,TEST @Value(json_index) = gust",wind_gust,"BOOL_OP,OR,COMPOSITE_TEST,""""""1"""""",TEST_CLAUSE,TEST @Value(json_index) = humidity",humidity,"BOOL_OP,OR,COMPOSITE_TEST,""""""1"""""",TEST_CLAUSE,TEST @Value(json_index) = sea_level",pressure_sl,"BOOL_OP,OR,COMPOSITE_TEST,""""""1"""""",TEST_CLAUSE,TEST @Value(json_index) = pressure",pressure,"BOOL_OP,OR,COMPOSITE_TEST,""""""1"""""",TEST_CLAUSE,TEST @Value(json_index) = speed",wind_speed,"BOOL_OP,OR,COMPOSITE_TEST,""""""1"""""",TEST_CLAUSE,TEST @Value(json_index) = temp",temp,"BOOL_OP,OR,COMPOSITE_TEST,""""""1"""""",TEST_CLAUSE,TEST @Value(json_index) = temp_max",temp_max,"BOOL_OP,OR,COMPOSITE_TEST,""""""1"""""",TEST_CLAUSE,TEST @Value(json_index) = temp_min",temp_min,"BOOL_OP,OR,COMPOSITE_TEST,""""""1"""""",TEST_CLAUSE,TEST @Value(json_index) = 3h_s",snow
    rain -> Counter_7
    cloudiness -> Counter_8
    wind_dir -> Counter_9
    temp_fl -> Counter_13
    pressure_gl -> Counter_14
    wind_gust -> Counter_15
    humidity -> Counter_16
    pressure_sl -> Counter_17
    pressure -> Counter_18
    wind_speed -> Counter_19
    temp -> Counter_20
    temp_max -> Counter_21
    temp_min -> Counter_22
    snow -> Counter_27
Counter_8
    CNT_ATTR = _count2
    SCOPE = Local
    START = 0
    -> AttributeManager_88
AttributeManager_88
    ATTR_TABLE:
      RENAME_SET_VALUE _response_body > cloudiness
      REMOVE json_type
      REMOVE json_index
      REMOVE fme_rejection_code
    USER_EXPOSED_ATTRIBUTES = _count2
    -> FeatureJoiner_29 [LEFT]
Counter_9
    CNT_ATTR = _count3
    SCOPE = Local
    START = 0
    -> AttributeManager_89
AttributeManager_89
    ATTR_TABLE:
      RENAME_SET_VALUE _response_body > wind_dir
      REMOVE json_type
      REMOVE json_index
      REMOVE fme_rejection_code
    USER_EXPOSED_ATTRIBUTES = _count3
    -> FeatureJoiner_29 [RIGHT]
FeatureJoiner_29
    ATTR_CONFLICT_RES = Use Left
    GEOMETRY_HANDLING = Use Left
    JOIN_KEYS = _count2 _count3 AUTO
    JOIN_MODE = Left
    JOINED -> FeatureJoiner_30 [LEFT]
Counter_13
    CNT_ATTR = _count4
    SCOPE = Local
    START = 0
    -> AttributeManager_94
AttributeManager_94
    ATTR_TABLE:
      RENAME_SET_VALUE _response_body > temp_fl
      REMOVE json_type
      REMOVE json_index
      REMOVE fme_rejection_code
    USER_EXPOSED_ATTRIBUTES = _count4
    -> FeatureJoiner_30 [RIGHT]
FeatureJoiner_30
    ATTR_CONFLICT_RES = Use Left
    GEOMETRY_HANDLING = Use Left
    JOIN_KEYS = _count2 _count4 AUTO
    JOIN_MODE = Left
    JOINED -> FeatureJoiner_33 [LEFT]
Counter_14
    CNT_ATTR = _count5
    SCOPE = Local
    START = 0
    -> AttributeManager_95
AttributeManager_95
    ATTR_TABLE:
      RENAME_SET_VALUE _response_body > pressure_gl
      REMOVE json_type
      REMOVE json_index
      REMOVE fme_rejection_code
    USER_EXPOSED_ATTRIBUTES = _count5
    -> FeatureJoiner_33 [RIGHT]
FeatureJoiner_33
    ATTR_CONFLICT_RES = Use Left
    GEOMETRY_HANDLING = Use Left
    JOIN_KEYS = _count4 _count5 AUTO
    JOIN_MODE = Left
    JOINED -> FeatureJoiner_34 [LEFT]
Counter_15
    CNT_ATTR = _count6
    SCOPE = Local
    START = 0
    -> AttributeManager_96
AttributeManager_96
    ATTR_TABLE:
      RENAME_SET_VALUE _response_body > wind_gust
      REMOVE json_type
      REMOVE json_index
      REMOVE fme_rejection_code
    USER_EXPOSED_ATTRIBUTES = _count5
    -> FeatureJoiner_34 [RIGHT]
FeatureJoiner_34
    ATTR_CONFLICT_RES = Use Left
    GEOMETRY_HANDLING = Use Left
    JOIN_KEYS = _count4 _count6 AUTO
    JOIN_MODE = Left
    JOINED -> FeatureJoiner_35 [LEFT]
Counter_16
    CNT_ATTR = _count7
    SCOPE = Local
    START = 0
    -> AttributeManager_97
AttributeManager_97
    ATTR_TABLE:
      RENAME_SET_VALUE _response_body > humidity
      REMOVE json_type
      REMOVE json_index
      REMOVE fme_rejection_code
    USER_EXPOSED_ATTRIBUTES = _count5
    -> FeatureJoiner_35 [RIGHT]
FeatureJoiner_35
    ATTR_CONFLICT_RES = Use Left
    GEOMETRY_HANDLING = Use Left
    JOIN_KEYS = _count4 _count7 AUTO
    JOIN_MODE = Left
    JOINED -> FeatureJoiner_36 [LEFT]
Counter_17
    CNT_ATTR = _count8
    SCOPE = Local
    START = 0
    -> AttributeManager_98
AttributeManager_98
    ATTR_TABLE:
      RENAME_SET_VALUE _response_body > pressure_sl
      REMOVE json_type
      REMOVE json_index
      REMOVE fme_rejection_code
    USER_EXPOSED_ATTRIBUTES = _count5
    -> FeatureJoiner_36 [RIGHT]
FeatureJoiner_36
    ATTR_CONFLICT_RES = Use Left
    GEOMETRY_HANDLING = Use Left
    JOIN_KEYS = _count4 _count8 AUTO
    JOIN_MODE = Left
    JOINED -> FeatureJoiner_37 [LEFT]
Counter_18
    CNT_ATTR = _count8
    SCOPE = Local
    START = 0
    -> AttributeManager_99
AttributeManager_99
    ATTR_TABLE:
      RENAME_SET_VALUE _response_body > pressure
      REMOVE json_type
      REMOVE json_index
      REMOVE fme_rejection_code
    USER_EXPOSED_ATTRIBUTES = _count5
    -> FeatureJoiner_37 [RIGHT]
FeatureJoiner_37
    ATTR_CONFLICT_RES = Use Left
    GEOMETRY_HANDLING = Use Left
    JOIN_KEYS = _count4 _count8 AUTO
    JOIN_MODE = Left
    JOINED -> FeatureJoiner_38 [LEFT]
Counter_19
    CNT_ATTR = _count9
    SCOPE = Local
    START = 0
    -> AttributeManager_100
AttributeManager_100
    ATTR_TABLE:
      RENAME_SET_VALUE _response_body > wind_speed
      REMOVE json_type
      REMOVE json_index
      REMOVE fme_rejection_code
    USER_EXPOSED_ATTRIBUTES = _count5
    -> FeatureJoiner_38 [RIGHT]
FeatureJoiner_38
    ATTR_CONFLICT_RES = Use Left
    GEOMETRY_HANDLING = Use Left
    JOIN_KEYS = _count4 _count9 AUTO
    JOIN_MODE = Left
    JOINED -> FeatureJoiner_39 [LEFT]
Counter_20
    CNT_ATTR = _count10
    SCOPE = Local
    START = 0
    -> AttributeManager_101
AttributeManager_101
    ATTR_TABLE:
      RENAME_SET_VALUE _response_body > temp
      REMOVE json_type
      REMOVE json_index
      REMOVE fme_rejection_code
    USER_EXPOSED_ATTRIBUTES = _count5
    -> FeatureJoiner_39 [RIGHT]
FeatureJoiner_39
    ATTR_CONFLICT_RES = Use Left
    GEOMETRY_HANDLING = Use Left
    JOIN_KEYS = _count4 _count10 AUTO
    JOIN_MODE = Left
    JOINED -> FeatureJoiner_40 [LEFT]
Counter_21
    CNT_ATTR = _count11
    SCOPE = Local
    START = 0
    -> AttributeManager_102
AttributeManager_102
    ATTR_TABLE:
      RENAME_SET_VALUE _response_body > temp_max
      REMOVE json_type
      REMOVE json_index
      REMOVE fme_rejection_code
    USER_EXPOSED_ATTRIBUTES = _count5
    -> FeatureJoiner_40 [RIGHT]
FeatureJoiner_40
    ATTR_CONFLICT_RES = Use Left
    GEOMETRY_HANDLING = Use Left
    JOIN_KEYS = _count4 _count11 AUTO
    JOIN_MODE = Left
    JOINED -> FeatureJoiner_41 [LEFT]
Counter_22
    CNT_ATTR = _count12
    SCOPE = Local
    START = 0
    -> AttributeManager_103
AttributeManager_103
    ATTR_TABLE:
      RENAME_SET_VALUE _response_body > temp_min
      REMOVE json_type
      REMOVE json_index
      REMOVE fme_rejection_code
    USER_EXPOSED_ATTRIBUTES = _count5
    -> FeatureJoiner_41 [RIGHT]
FeatureJoiner_41
    ATTR_CONFLICT_RES = Use Left
    GEOMETRY_HANDLING = Use Left
    JOIN_KEYS = _count4 _count12 AUTO
    JOIN_MODE = Left
    JOINED -> AttributeManager_104
AttributeManager_104
    ATTR_TABLE:
      REMOVE _count3
      REMOVE _count4
      REMOVE _count5
      REMOVE _count6
      REMOVE _count7
      REMOVE _count8
      REMOVE _count9
      REMOVE _count10
      REMOVE _count11
      REMOVE _count12
    -> FeatureJoiner_42 [LEFT]
Counter_7
    CNT_ATTR = _count99
    DOMAIN = counter
    SCOPE = Global
    START = 0
    -> AttributeManager_87
AttributeManager_87
    ATTR_TABLE:
      RENAME_SET_VALUE _response_body > rain
      REMOVE json_type
      REMOVE json_index
      REMOVE fme_rejection_code
    USER_EXPOSED_ATTRIBUTES = _count1
    -> FeatureJoiner_44 [RIGHT]
Counter_27
    CNT_ATTR = _count9999
    SCOPE = Local
    START = 0
    -> AttributeManager_113
AttributeManager_113
    ATTR_TABLE:
      RENAME_SET_VALUE _response_body > snow
      REMOVE json_type
      REMOVE json_index
      REMOVE fme_rejection_code
    USER_EXPOSED_ATTRIBUTES = _count1
    -> FeatureJoiner_47 [RIGHT]
TestFilter_16
    DEFAULT_VALUE = <UNFILTERED>
    TEST_LIST = "BOOL_OP,OR,COMPOSITE_TEST,""""""1"""""",TEST_CLAUSE,TEST @Value(json_index) = dt",dt,"BOOL_OP,OR,COMPOSITE_TEST,""""""1"""""",TEST_CLAUSE,TEST @Value(json_index) = dt_txt",dt_txt,"BOOL_OP,OR,COMPOSITE_TEST,""""""1"""""",TEST_CLAUSE,TEST @Value(json_index) = visibility",visbility,"BOOL_OP,OR,COMPOSITE_TEST,""""""1"""""",TEST_CLAUSE,TEST @Value(json_index) = pop",pop
    dt -> Counter_4
    dt_txt -> Counter_5
    visbility -> Counter_6
    pop -> Counter_10
Counter_4
    CNT_ATTR = _count00
    SCOPE = Local
    START = 0
    -> AttributeManager_8
AttributeManager_8
    ATTR_TABLE:
      RENAME_SET_VALUE _response_body > dt
      REMOVE json_type
      REMOVE json_index
      REMOVE fme_rejection_code
    USER_EXPOSED_ATTRIBUTES = _count00
    -> FeatureJoiner_27 [LEFT]
Counter_5
    CNT_ATTR = _count01
    SCOPE = Local
    START = 0
    -> AttributeManager_85
AttributeManager_85
    ATTR_TABLE:
      RENAME_SET_VALUE _response_body > dt_txt
      REMOVE json_type
      REMOVE json_index
      REMOVE fme_rejection_code
    USER_EXPOSED_ATTRIBUTES = _count01
    -> FeatureJoiner_27 [RIGHT]
FeatureJoiner_27
    ATTR_CONFLICT_RES = Use Left
    GEOMETRY_HANDLING = Use Left
    JOIN_KEYS = _count00 _count01 AUTO
    JOIN_MODE = Left
    JOINED -> FeatureJoiner_28 [LEFT]
Counter_6
    CNT_ATTR = _count02
    SCOPE = Local
    START = 0
    -> AttributeManager_86
AttributeManager_86
    ATTR_TABLE:
      RENAME_SET_VALUE _response_body > visbility
      REMOVE json_type
      REMOVE json_index
      REMOVE fme_rejection_code
    USER_EXPOSED_ATTRIBUTES = _count02
    -> FeatureJoiner_28 [RIGHT]
FeatureJoiner_28
    ATTR_CONFLICT_RES = Use Left
    GEOMETRY_HANDLING = Use Left
    JOIN_KEYS = _count00 _count02 AUTO
    JOIN_MODE = Left
    JOINED -> FeatureJoiner_31 [LEFT]
Counter_10
    CNT_ATTR = _count03
    SCOPE = Local
    START = 0
    -> AttributeManager_90
AttributeManager_90
    ATTR_TABLE:
      RENAME_SET_VALUE _response_body > pop
      REMOVE json_type
      REMOVE json_index
      REMOVE fme_rejection_code
    USER_EXPOSED_ATTRIBUTES = _count03
    -> FeatureJoiner_31 [RIGHT]
FeatureJoiner_31
    ATTR_CONFLICT_RES = Use Left
    GEOMETRY_HANDLING = Use Left
    JOIN_KEYS = _count00 _count03 AUTO
    JOIN_MODE = Left
    JOINED -> AttributeManager_105
AttributeManager_105
    ATTR_TABLE:
      REMOVE _count01
      REMOVE _count02
      REMOVE _count03
    -> FeatureJoiner_42 [RIGHT]
FeatureJoiner_42
    ATTR_CONFLICT_RES = Use Left
    GEOMETRY_HANDLING = Use Left
    JOIN_KEYS = _count2 _count00 AUTO
    JOIN_MODE = Inner
    JOINED -> FeatureJoiner_45 [LEFT]
Logger_2
    LOG_FEATURE = LOG_ONLY
    MAXCOORDS = 20
    MAXFEATS = 20
    MESSAGE = Feature is:
    SEVERITY = INFO
TestFilter_18
    DEFAULT_VALUE = <UNFILTERED>
    TEST_LIST:
      "BOOL_OP,OR,COMPOSITE_TEST,""""""1 OR 2"""""",TEST_CLAUSE,TEST @Value(json_index) = dt
      TEST @Value(json_index) = rain",rain
    rain -> Counter_11
Counter_11
    CNT_ATTR = _count
    SCOPE = Local
    START = 0
    -> TestFilter_20
TestFilter_20
    DEFAULT_VALUE = <UNFILTERED>
    TEST_LIST = "BOOL_OP,OR,COMPOSITE_TEST,""""""1"""""",TEST_CLAUSE,TEST @Value(json_index) = rain",rain
    rain -> Counter_12
Counter_12
    CNT_ATTR = _countrain
    SCOPE = Local
    START = 0
    -> AttributeManager_92
AttributeManager_92
    ATTR_TABLE:
      REMOVE _response_body
      REMOVE json_type
      REMOVE json_index
      SET_TO rain = 1
      SET_TO indexrain = @Evaluate(@Value(_count)-@Value(_countrain)-1)
    -> AttributeManager_91
AttributeManager_91
    ATTR_TABLE:
      REMOVE _count
      RENAME_SET_VALUE rain > rainevent
      REMOVE _countrain
      SET_TO join = 0
    -> FeatureJoiner_32 [RIGHT]
    -> Counter_23
Counter_23
    CNT_ATTR = _count_000
    SCOPE = Local
    START = 0
    -> FeatureJoiner_44 [LEFT]
FeatureJoiner_44
    ATTR_CONFLICT_RES = Use Left
    GEOMETRY_HANDLING = Use Left
    JOIN_KEYS = _count_000 _count99 AUTO
    JOIN_MODE = Inner
    JOINED -> FeatureJoiner_43 [RIGHT]
TestFilter_21
    DEFAULT_VALUE = <UNFILTERED>
    TEST_LIST:
      "BOOL_OP,OR,COMPOSITE_TEST,""""""1 OR 2"""""",TEST_CLAUSE,TEST @Value(json_index) = dt
      TEST @Value(json_index) = snow",snow
    snow -> Counter_24
Counter_24
    CNT_ATTR = _count0000
    SCOPE = Local
    START = 0
    -> TestFilter_19
TestFilter_19
    DEFAULT_VALUE = <UNFILTERED>
    TEST_LIST = "BOOL_OP,OR,COMPOSITE_TEST,""""""1"""""",TEST_CLAUSE,TEST @Value(json_index) = snow",snow
    snow -> Counter_25
Counter_25
    CNT_ATTR = _countrain
    SCOPE = Local
    START = 0
    -> AttributeManager_109
AttributeManager_109
    ATTR_TABLE:
      REMOVE _response_body
      REMOVE json_type
      REMOVE json_index
      SET_TO snow = 1
      SET_TO indexsnow = @Evaluate(@Value(_count0000)-@Value(_countrain)-1)
    -> AttributeManager_110
AttributeManager_110
    ATTR_TABLE:
      REMOVE _countrain
      SET_TO join = 0
      RENAME_SET_VALUE snow > snowenvent
    USER_EXPOSED_ATTRIBUTES = snow
    -> FeatureJoiner_46 [RIGHT]
    -> Counter_26
Counter_26
    CNT_ATTR = _count_000
    SCOPE = Local
    START = 0
    -> FeatureJoiner_47 [LEFT]
FeatureJoiner_47
    ATTR_CONFLICT_RES = Use Left
    GEOMETRY_HANDLING = Use Left
    JOIN_KEYS = _count_000 _count9999 AUTO
    JOIN_MODE = Inner
    JOINED -> FeatureJoiner_48 [RIGHT]
Logger
    LOG_FEATURE = LOG_ONLY
    MAXCOORDS = 20
    MAXFEATS = 20
    MESSAGE = Feature is:
    SEVERITY = INFO
Creator_4
    GEOMTYPE = Geometry Object
    NUM = 40
    CREATED -> AttributeManager_111
AttributeManager_111
    ATTR_TABLE = SET_TO join = 0
    -> FeatureJoiner_46 [LEFT]
FeatureJoiner_46
    ATTR_CONFLICT_RES = Use Left
    GEOMETRY_HANDLING = Use Left
    JOIN_KEYS = _creation_instance indexsnow AUTO
    JOIN_MODE = Full
    JOINED -> AttributeManager_112
AttributeManager_112
    ATTR_TABLE:
      REMOVE join
      REMOVE indexsnow
      SET_TO snowenvent = FME_CONDITIONAL:DEFAULT_VALUE'_FME_NO_OP_'BOOL_OP;OR;COMPOSITE_TEST;1;TEST snowenvent ATTRIBUTE_VALUE_NULL _FME_BLANK_STRING_'0'FME_NUM_CONDITIONS2___
    -> FeatureJoiner_48 [LEFT]
FeatureJoiner_48
    ATTR_CONFLICT_RES = Use Left
    GEOMETRY_HANDLING = Use Left
    JOIN_KEYS = _creation_instance indexsnow AUTO
    JOIN_MODE = Full
    JOINED -> AttributeManager_114
AttributeManager_114
    ATTR_TABLE:
      REMOVE join
      REMOVE _count_000
      REMOVE _count1
      REMOVE _count0000
      REMOVE snowenvent
      REMOVE indexsnow
      SET_TO snow = FME_CONDITIONAL:DEFAULT_VALUE'_FME_NO_OP_'BOOL_OP;OR;COMPOSITE_TEST;1;TEST snow ATTRIBUTE_VALUE_NULL _FME_BLANK_STRING_'0'FME_NUM_CONDITIONS2___
      REMOVE _count111
      REMOVE _count9999
    USER_EXPOSED_ATTRIBUTES = rain,rainevent,indexrain,_count111
    -> FeatureJoiner_49 [RIGHT]
Creator_3
    GEOMTYPE = Geometry Object
    NUM = 40
    CREATED -> AttributeManager_93
AttributeManager_93
    ATTR_TABLE = SET_TO join = 0
    -> FeatureJoiner_32 [LEFT]
FeatureJoiner_32
    ATTR_CONFLICT_RES = Use Left
    GEOMETRY_HANDLING = Use Left
    JOIN_KEYS = _creation_instance indexrain AUTO
    JOIN_MODE = Full
    JOINED -> AttributeManager_107
AttributeManager_107
    ATTR_TABLE:
      REMOVE join
      REMOVE indexrain
      SET_TO rainevent = FME_CONDITIONAL:DEFAULT_VALUE'_FME_NO_OP_'BOOL_OP;OR;COMPOSITE_TEST;1;TEST rainevent ATTRIBUTE_VALUE_NULL _FME_BLANK_STRING_'0'FME_NUM_CONDITIONS2___
    -> FeatureJoiner_43 [LEFT]
FeatureJoiner_43
    ATTR_CONFLICT_RES = Use Left
    GEOMETRY_HANDLING = Use Left
    JOIN_KEYS = _creation_instance indexrain AUTO
    JOIN_MODE = Full
    JOINED -> AttributeManager_108
AttributeManager_108
    ATTR_TABLE:
      REMOVE rainevent
      REMOVE indexrain
      REMOVE join
      REMOVE _count_000
      SET_TO rain = FME_CONDITIONAL:DEFAULT_VALUE'_FME_NO_OP_'BOOL_OP;OR;COMPOSITE_TEST;1;TEST rain ATTRIBUTE_VALUE_NULL _FME_BLANK_STRING_'0'FME_NUM_CONDITIONS2___
      REMOVE _count1
    -> FeatureJoiner_45 [RIGHT]
FeatureJoiner_45
    ATTR_CONFLICT_RES = Use Left
    GEOMETRY_HANDLING = Use Left
    JOIN_KEYS = _count2 _creation_instance AUTO
    JOIN_MODE = Inner
    JOINED -> FeatureJoiner_49 [LEFT]
FeatureJoiner_49
    ATTR_CONFLICT_RES = Use Left
    GEOMETRY_HANDLING = Use Left
    JOIN_KEYS = _count2 _creation_instance AUTO
    JOIN_MODE = Inner
    JOINED -> AttributeManager_106

FME custom transformer deg2num
Get tile number from coordinates(lat_deg
lon_deg)

Parameters:
- LAT_DEG =
- LON_DEG =
- ZOOM =

Input (input)
    -> AttributeManager_2
AttributeManager_2
    ATTR_TABLE:
      SET_TO lat_rad = @Evaluate(@degToRad(@Value(lat_deg)))
      SET_TO n = @Evaluate(@pow(2,@Value(zoom)))
      SET_TO sinh = @Evaluate(@log(@tan(@Value(lat_rad))+@sqrt(@pow(@tan(@Value(lat_rad)),2)+1)))
      SET_TO xtile = @Evaluate(@int((@Value(lon_deg)+180)/360*@Value(n)))
      SET_TO ytile = @int((1-@Value(sinh)/@pi())/2*@Value(n))
    -> Output (output)
Output (output)

FME custom transformer ISO_merger

Parameters:
- AREA_KM2 =
- B_PER_CAP =
- CONTINENT =
- COUNTRY =
- COUNTRY_2 =
- COUNTRY_COMP =
- COUNTY =
- IDH =
- ISO2 =
- ISO3 =
- JOIN =
- LAT_LON =
- MAX_X =
- MAX_Y =
- MIN_X =
- MIN_Y =
- OSMFR =
- POPDENS_CAP_KM2 =
- POPULATION =
- REGION =
- SIZE_MB =
- STATE =
- STATEANDCOUNTRY =
- SUBREGION =
- URL =
- _COPYNUM =
- _CREATION_INSTANCE =
- _LENGTH =
- _LENGTH.MAX =
- _OVERLAPS =
- _X =
- _Y =

AttributeManager (input)
    -> AttributeManager_41
AttributeManager_41
    ATTR_TABLE:
      REMOVE country
      REMOVE state
      REMOVE county
      REMOVE region
      REMOVE Country
      REMOVE Continent
      REMOVE Population
      REMOVE Size_MB
      REMOVE b_per_cap
      REMOVE area_km2
      REMOVE PopDens_cap_km2
      REMOVE ISO2
      REMOVE IDH
      REMOVE OSMFR
      REMOVE subregion
      REMOVE stateANDcountry
      REMOVE Country_comp
      REMOVE join
      REMOVE _creation_instance
      REMOVE _min_max_BB{}
      REMOVE _copynum
      REMOVE lat_lon
      REMOVE _length
      REMOVE _length.max
      REMOVE _overlaps
      REMOVE _x
      REMOVE _y
    -> AttributeManager_75
    -> FeatureJoiner_26 [RIGHT]
AttributeManager_75
    ATTR_TABLE:
      REMOVE url
      REMOVE max_x
      REMOVE min_x
      REMOVE max_y
    -> DuplicateFilter_6
DuplicateFilter_6
    INPUT_ORDERED_CHOICE = No
    KEYATTR = ISO3
    UNIQUE -> Counter_3
Counter_3
    CNT_ATTR = _count
    DOMAIN = counter
    SCOPE = Global
    START = 0
    -> StatisticsCalculator_4
StatisticsCalculator_4
    CALCULATION_MODE = NUMERIC
    FEAT_STATS = _count,NUMERIC_MODE,,MAX,,,,,,,,,,,
    COMPLETE -> TestFilter_15
TestFilter_15
    DEFAULT_VALUE = <UNFILTERED>
    TEST_LIST = "BOOL_OP,OR,COMPOSITE_TEST,""""""1"""""",TEST_CLAUSE,TEST @Value(_count) = 0",ISO0,"BOOL_OP,OR,COMPOSITE_TEST,""""""1"""""",TEST_CLAUSE,TEST @Value(_count) = 1",ISO1,"BOOL_OP,OR,COMPOSITE_TEST,""""""1"""""",TEST_CLAUSE,TEST @Value(_count) = 2",ISO2,"BOOL_OP,OR,COMPOSITE_TEST,""""""1"""""",TEST_CLAUSE,TEST @Value(_count) = 3",ISO3,"BOOL_OP,OR,COMPOSITE_TEST,""""""1"""""",TEST_CLAUSE,TEST @Value(_count) = 4",ISO4,"BOOL_OP,OR,COMPOSITE_TEST,""""""1"""""",TEST_CLAUSE,TEST @Value(_count) = 5",ISO5,"BOOL_OP,OR,COMPOSITE_TEST,""""""1"""""",TEST_CLAUSE,TEST @Value(_count) = 6",ISO6,"BOOL_OP,OR,COMPOSITE_TEST,""""""1"""""",TEST_CLAUSE,TEST @Value(_count) = 7",ISO7
    ISO0 -> AttributeManager_76
    ISO1 -> AttributeManager_77
    ISO2 -> AttributeManager_78
    ISO3 -> AttributeManager_79
    ISO4 -> AttributeManager_80
    ISO5 -> AttributeManager_81
    ISO6 -> AttributeManager_82
    ISO7 -> AttributeManager_83
AttributeManager_83
    ATTR_TABLE = RENAME_SET_VALUE ISO3 > iso7
    -> FeatureJoiner_25 [RIGHT]
AttributeManager_82
    ATTR_TABLE = RENAME_SET_VALUE ISO3 > iso6
    -> FeatureJoiner_24 [RIGHT]
AttributeManager_81
    ATTR_TABLE = RENAME_SET_VALUE ISO3 > iso5
    -> FeatureJoiner_23 [RIGHT]
AttributeManager_80
    ATTR_TABLE = RENAME_SET_VALUE ISO3 > iso4
    -> FeatureJoiner_22 [RIGHT]
AttributeManager_79
    ATTR_TABLE = RENAME_SET_VALUE ISO3 > iso3
    -> FeatureJoiner_21 [RIGHT]
AttributeManager_78
    ATTR_TABLE = RENAME_SET_VALUE ISO3 > iso2
    -> FeatureJoiner_20 [RIGHT]
AttributeManager_77
    ATTR_TABLE = RENAME_SET_VALUE ISO3 > iso1
    -> FeatureJoiner_19 [RIGHT]
AttributeManager_76
    ATTR_TABLE = RENAME_SET_VALUE ISO3 > iso0
    -> FeatureJoiner_19 [LEFT]
FeatureJoiner_19
    ATTR_CONFLICT_RES = Use Left
    GEOMETRY_HANDLING = Use Left
    JOIN_KEYS = _count.max _count.max AUTO
    JOIN_MODE = Inner
    JOINED -> FeatureJoiner_20 [LEFT]
    UNJOINED_LEFT -> AttributeManager_84
FeatureJoiner_20
    ATTR_CONFLICT_RES = Use Left
    GEOMETRY_HANDLING = Use Left
    JOIN_KEYS = _count.max _count.max AUTO
    JOIN_MODE = Inner
    JOINED -> FeatureJoiner_21 [LEFT]
    UNJOINED_LEFT -> StringConcatenator
FeatureJoiner_21
    ATTR_CONFLICT_RES = Use Left
    GEOMETRY_HANDLING = Use Left
    JOIN_KEYS = _count.max _count.max AUTO
    JOIN_MODE = Inner
    JOINED -> FeatureJoiner_22 [LEFT]
    UNJOINED_LEFT -> StringConcatenator_2
FeatureJoiner_22
    ATTR_CONFLICT_RES = Use Left
    GEOMETRY_HANDLING = Use Left
    JOIN_KEYS = _count.max _count.max AUTO
    JOIN_MODE = Inner
    JOINED -> FeatureJoiner_23 [LEFT]
    UNJOINED_LEFT -> StringConcatenator_3
Note: Computation of the time
FeatureJoiner_23
    ATTR_CONFLICT_RES = Use Left
    GEOMETRY_HANDLING = Use Left
    JOIN_KEYS = _count.max _count.max AUTO
    JOIN_MODE = Inner
    JOINED -> FeatureJoiner_24 [LEFT]
    UNJOINED_LEFT -> StringConcatenator_4
FeatureJoiner_24
    ATTR_CONFLICT_RES = Use Left
    GEOMETRY_HANDLING = Use Left
    JOIN_KEYS = _count.max _count.max AUTO
    JOIN_MODE = Inner
    JOINED -> FeatureJoiner_25 [LEFT]
    UNJOINED_LEFT -> StringConcatenator_5
FeatureJoiner_25
    ATTR_CONFLICT_RES = Use Left
    GEOMETRY_HANDLING = Use Left
    JOIN_KEYS = _count.max _count.max AUTO
    JOIN_MODE = Inner
    JOINED -> StringConcatenator_7
    UNJOINED_LEFT -> StringConcatenator_6
StringConcatenator_7
    ACTION = Create New Attribute
    PARM_LINE = fme_basicstring:12%1%12%1%12%1%12%1%12%0%12%1%12%1%12:@Value(iso0)_@Value(iso1)_@Value(iso2)_@Value(iso3)_@Value(iso4)@Value(iso5)_@Value(iso6)_@Value(iso7)
    VAL_ATTR = _result
    -> AttributeManager_84
StringConcatenator_6
    ACTION = Create New Attribute
    PARM_LINE = fme_basicstring:12%1%12%1%12%1%12%1%12%0%12%1%12:@Value(iso0)_@Value(iso1)_@Value(iso2)_@Value(iso3)_@Value(iso4)@Value(iso5)_@Value(iso6)
    VAL_ATTR = _result
    -> AttributeManager_84
StringConcatenator_5
    ACTION = Create New Attribute
    PARM_LINE = fme_basicstring:12%1%12%1%12%1%12%1%12%0%12:@Value(iso0)_@Value(iso1)_@Value(iso2)_@Value(iso3)_@Value(iso4)@Value(iso5)
    VAL_ATTR = _result
    -> AttributeManager_84
StringConcatenator_4
    ACTION = Create New Attribute
    PARM_LINE = fme_basicstring:12%1%12%1%12%1%12%1%12:@Value(iso0)_@Value(iso1)_@Value(iso2)_@Value(iso3)_@Value(iso4)
    VAL_ATTR = _result
    -> AttributeManager_84
StringConcatenator_3
    ACTION = Create New Attribute
    PARM_LINE = fme_basicstring:12%1%12%1%12%1%12:@Value(iso0)_@Value(iso1)_@Value(iso2)_@Value(iso3)
    VAL_ATTR = _result
    -> AttributeManager_84
StringConcatenator_2
    ACTION = Create New Attribute
    PARM_LINE = fme_basicstring:12%1%12%1%12:@Value(iso0)_@Value(iso1)_@Value(iso2)
    VAL_ATTR = _result
    -> AttributeManager_84
StringConcatenator
    ACTION = Create New Attribute
    PARM_LINE = fme_basicstring:12%1%12:@Value(iso0)_@Value(iso1)
    VAL_ATTR = _result
    -> AttributeManager_84
AttributeManager_84
    ATTR_TABLE:
      REMOVE iso0
      REMOVE _count
      REMOVE iso1
      RENAME_SET_VALUE _result > ISO_merge
      REMOVE iso2
      REMOVE iso3
      REMOVE iso4
      REMOVE iso5
      REMOVE iso6
      REMOVE iso7
    -> FeatureJoiner_26 [LEFT]
FeatureJoiner_26
    ATTR_CONFLICT_RES = Use Left
    GEOMETRY_HANDLING = Use Left
    JOIN_KEYS = min_y min_y AUTO
    JOIN_MODE = Full
    JOINED -> AttributeManager_126
AttributeManager_126
    ATTR_TABLE = SET_TO ISO_merge = FME_CONDITIONAL:DEFAULT_VALUE'_FME_NO_OP_'BOOL_OP;OR;COMPOSITE_TEST;1;TEST ISO_merge ATTRIBUTE_IS_MISSING _FME_BLANK_STRING_'@Value(ISO3)'FME_NUM_CONDITIONS2___
    -> DuplicateFilter_4
    -> AttributeManager_126_:_Output (output)
DuplicateFilter_4
    INPUT_ORDERED_CHOICE = No
    KEYATTR = max_x max_y min_x min_y
    UNIQUE -> DuplicateFilter_4_:_Unique (output)
DuplicateFilter_4_:_Unique (output)
AttributeManager_126_:_Output (output)

FME custom transformer FuzzyStringComparer
This transformer uses the Python difflib module to compare two string attributes and calculate a similarity ratio. The similarity ratio describes the closeness of the match between the two strings. The higher the value, the closer the match (1 = exact).
If desired, the transformer will also output a comparison string. This is a two line string illustrating the differences between the two input strings by lining up the matching sections. When displaying the comparison string, you will get the best results using a non-proportional font like Courier.
Example:
string 1 = 'South Dayton Street'
string 2 = 'S Dayton St.'
The comparison string would be:
South Dayton St reet
S        Dayton St.
Input Ports 
Input - This transformer will accept any feature containing attributes to compare.
Output Ports 
Output - Features are output with a new attribute added to store the calculated comparison ratio value.
Parameters 
String 1 Attribute - The name of the attribute containing the first string to compare.
String 2 Attribute - The name of the attribute containing the second string to compare.
Output Ratio Attribute - A text field to set the name of the attribute that will be created to store the calculated ratio value. 
Output Comparison Attribute- An optional text field to set the name of the attribute that will be created to store the comparison string.

Parameters:
- DEST_ATTR =
- DEST_COMP =
- STRING1 =
- STRING2 =

Input (input)
    -> AttributeCreator
Note: Initialize attributes
AttributeCreator
    ATTR_TABLE:
      SET_TO FuzzyStringCompare.string1 = $(STRING1)
      SET_TO FuzzyStringCompare.string2 = $(STRING2)
    -> PythonCaller
Note: Calculate similarity ratio
PythonCaller
    NEW_ATTRIBUTES = FuzzyStringCompare.ratio
    PYTHONSOURCE:
      import difflib
      import sys

      def FuzzyStringCompare(feature):
          # get strings from attributes
          string1 = feature.getAttribute('FuzzyStringCompare.string1')
          string2 = feature.getAttribute('FuzzyStringCompare.string2')
          version = sys.version_info[0]

          if string1 != None and string2 != None:
              # convert to unicode strings if necessary
              if version > 2:
                  if not isinstance(string1, str):
                      string1 = '{}'.format(string1)
                  if not isinstance(string2, str):
                      string2 = '{}'.format(string2)
              else:
                  if not isinstance(string1, unicode):
                      string1 = u'{}'.format(string1)
                  if not isinstance(string2, unicode):
                      string2 = u'{}'.format(string2)

              # calculate difference ratio
              s = difflib.SequenceMatcher(None,string1.lower(),string2.lower())
              ratio = s.ratio()

              # update input strings
              differ = difflib.ndiff(string1,string2)
              diff1 = ''
              diff2 = ''
              for line in differ:
                  if line[0] == '-':
                      diff1 = diff1 + (line[2])
                      diff2 = diff2 + ' '
                  elif line[0] == '+':
                      diff1 = diff1 + ' '
                      diff2 = diff2 + (line[2])
                  else:
                      diff1 = diff1 + (line[2])
                      diff2 = diff2 + (line[2])

              # set new attributes on feature
              feature.setAttribute('FuzzyStringCompare.ratio',ratio)
              feature.setAttribute('FuzzyStringCompare.string1',diff1)
              feature.setAttribute('FuzzyStringCompare.string2',diff2)
    PYTHONSYMBOL = FuzzyStringCompare
    -> AttributeCreator_2
Note: Set output ratio attribute name
AttributeCreator_2
    ATTR_TABLE = SET_TO $(DEST_ATTR) = @Value(FuzzyStringCompare.ratio)
    -> Tester
Note: If comparison name set, / add comparison string
Tester
    BOOL_OP = OR
    COMPOSITE_TEST = 1
    TEST_CLAUSE = TEST $(DEST_COMP) NOT_ATTRIBUTE_HAS_VALUE ""
    TEST_MODE = TEST
    PASSED -> AttributeRemover
    FAILED -> AttributeCreator_3
Note: comparision string
AttributeCreator_3
    ATTR_TABLE:
      SET_TO $(DEST_COMP) = @Value(FuzzyStringCompare.string1)
        @Value(FuzzyStringCompare.string2)
    -> AttributeRemover
Note: Clean up temporary attributes.
AttributeRemover
    REMOVE_ATTRS = FuzzyStringCompare.ratio,FuzzyStringCompare.string1,FuzzyStringCompare.string2
    -> Output (output)
Output (output)

FME custom transformer num2deg
Tile number to degrees (lat
lon)

Parameters:
- LAT_DEG =
- LON_DEG =
- XTILE =
- YTILE =
- YTILE_B =
- ZOOM =
- _CREATION_INSTANCE =

Input (input)
    -> AttributeManager_2
AttributeManager_2
    ATTR_TABLE:
      SET_TO n = @Evaluate(@pow(2,@Value(zoom)))
      SET_TO lat_rad = @Evaluate(@atan(@sinh(@pi() * (1 - 2 *@Value(ytile)/@Value(n)))))
      SET_TO lat_deg = @Evaluate(@radToDeg(@Value(lat_rad)))
      SET_TO lon_deg = @Evaluate(@Value(xtile)/@Value(n) * 360.0 - 180.0)
      SET_TO lat_rad_b = @Evaluate(@atan(@sinh(@pi() * (1 - 2 *@Value(ytile_b)/@Value(n)))))
      SET_TO lat_deg_b = @Evaluate(@radToDeg(@Value(lat_rad_b)))
    -> Output (output)
Output (output)

FME custom transformer URL managment

Parameters:
- ISO3 =
- MAX_X =
- MAX_Y =
- MIN_X =
- MIN_Y =
- URL =

Counter (input)
    -> Counter
Counter
    CNT_ATTR = _count
    DOMAIN = counter
    SCOPE = Global
    START = 0
    -> StatisticsCalculator_2
StatisticsCalculator_2
    CALCULATION_MODE = NUMERIC
    FEAT_STATS = _count,NUMERIC_MODE,,MAX,,,,,,,,,,,
    COMPLETE -> TestFilter_13
TestFilter_13
    DEFAULT_VALUE = <UNFILTERED>
    TEST_LIST = "BOOL_OP,OR,COMPOSITE_TEST,""""""1"""""",TEST_CLAUSE,TEST @Value(_count) = 0",url0,"BOOL_OP,OR,COMPOSITE_TEST,""""""1"""""",TEST_CLAUSE,TEST @Value(_count) = 1",url1,"BOOL_OP,OR,COMPOSITE_TEST,""""""1"""""",TEST_CLAUSE,TEST @Value(_count) = 2",url2,"BOOL_OP,OR,COMPOSITE_TEST,""""""1"""""",TEST_CLAUSE,TEST @Value(_count) = 3",url3,"BOOL_OP,OR,COMPOSITE_TEST,""""""1"""""",TEST_CLAUSE,TEST @Value(_count) = 4",url4,"BOOL_OP,OR,COMPOSITE_TEST,""""""1"""""",TEST_CLAUSE,TEST @Value(_count) = 5",url5,"BOOL_OP,OR,COMPOSITE_TEST,""""""1"""""",TEST_CLAUSE,TEST @Value(_count) = 6",url6,"BOOL_OP,OR,COMPOSITE_TEST,""""""1"""""",TEST_CLAUSE,TEST @Value(_count) = 7",url7
    url0 -> AttributeManager_42
    url1 -> AttributeManager_43
    url2 -> AttributeManager_44
    url3 -> AttributeManager_45
    url4 -> AttributeManager_46
    url5 -> AttributeManager_47
    url6 -> AttributeManager_48
    url7 -> AttributeManager_49
AttributeManager_49
    ATTR_TABLE = RENAME_SET_VALUE url > url8
    -> FeatureJoiner_11 [RIGHT]
AttributeManager_48
    ATTR_TABLE = RENAME_SET_VALUE url > url7
    -> FeatureJoiner_10 [RIGHT]
AttributeManager_47
    ATTR_TABLE = RENAME_SET_VALUE url > url6
    -> FeatureJoiner_9 [RIGHT]
AttributeManager_46
    ATTR_TABLE = RENAME_SET_VALUE url > url5
    -> FeatureJoiner_8 [RIGHT]
AttributeManager_45
    ATTR_TABLE = RENAME_SET_VALUE url > url4
    -> FeatureJoiner_7 [RIGHT]
AttributeManager_44
    ATTR_TABLE = RENAME_SET_VALUE url > url3
    -> FeatureJoiner_6 [RIGHT]
AttributeManager_42
    ATTR_TABLE = RENAME_SET_VALUE url > url1
    -> FeatureJoiner_2 [LEFT]
AttributeManager_43
    ATTR_TABLE = RENAME_SET_VALUE url > url2
    -> FeatureJoiner_2 [RIGHT]
FeatureJoiner_2
    ATTR_CONFLICT_RES = Use Left
    GEOMETRY_HANDLING = Use Left
    JOIN_KEYS = max_x max_x AUTO
    JOIN_MODE = Inner
    JOINED -> FeatureJoiner_6 [LEFT]
    UNJOINED_LEFT -> AttributeManager_52
AttributeManager_52
    ATTR_TABLE:
      SET_TO url3 = @Value(url1)
      SET_TO url4 = @Value(url1)
      SET_TO url5 = @Value(url1)
      SET_TO url6 = @Value(url1)
      SET_TO url7 = @Value(url1)
      SET_TO url8 = @Value(url1)
      SET_TO url2 = @Value(url1)
    -> AttributeManager_52_:_Output (output)
AttributeManager_52_:_Output (output)
FeatureJoiner_6
    ATTR_CONFLICT_RES = Use Left
    GEOMETRY_HANDLING = Use Left
    JOIN_KEYS = max_x max_x AUTO
    JOIN_MODE = Inner
    JOINED -> FeatureJoiner_7 [LEFT]
    UNJOINED_LEFT -> AttributeManager_51
AttributeManager_51
    ATTR_TABLE:
      SET_TO url3 = @Value(url1)
      SET_TO url4 = @Value(url1)
      SET_TO url5 = @Value(url1)
      SET_TO url6 = @Value(url1)
      SET_TO url7 = @Value(url1)
      SET_TO url8 = @Value(url1)
    -> AttributeManager_51_:_Output (output)
AttributeManager_51_:_Output (output)
FeatureJoiner_7
    ATTR_CONFLICT_RES = Use Left
    GEOMETRY_HANDLING = Use Left
    JOIN_KEYS = max_x max_x AUTO
    JOIN_MODE = Inner
    JOINED -> FeatureJoiner_8 [LEFT]
    UNJOINED_LEFT -> AttributeManager_50
AttributeManager_50
    ATTR_TABLE:
      SET_TO url4 = @Value(url1)
      SET_TO url5 = @Value(url1)
      SET_TO url6 = @Value(url1)
      SET_TO url7 = @Value(url1)
      SET_TO url8 = @Value(url1)
    -> AttributeManager_50_:_Output (output)
AttributeManager_50_:_Output (output)
FeatureJoiner_8
    ATTR_CONFLICT_RES = Use Left
    GEOMETRY_HANDLING = Use Left
    JOIN_KEYS = max_x max_x AUTO
    JOIN_MODE = Inner
    JOINED -> FeatureJoiner_9 [LEFT]
    UNJOINED_LEFT -> AttributeManager_53
AttributeManager_53
    ATTR_TABLE:
      SET_TO url5 = @Value(url1)
      SET_TO url6 = @Value(url1)
      SET_TO url7 = @Value(url1)
      SET_TO url8 = @Value(url1)
    -> AttributeManager_53_:_Output (output)
AttributeManager_53_:_Output (output)
FeatureJoiner_9
    ATTR_CONFLICT_RES = Use Left
    GEOMETRY_HANDLING = Use Left
    JOIN_KEYS = max_x max_x AUTO
    JOIN_MODE = Inner
    JOINED -> FeatureJoiner_10 [LEFT]
    UNJOINED_LEFT -> AttributeManager_54
AttributeManager_54
    ATTR_TABLE:
      SET_TO url6 = @Value(url1)
      SET_TO url7 = @Value(url1)
      SET_TO url8 = @Value(url1)
    -> AttributeManager_54_:_Output (output)
AttributeManager_54_:_Output (output)
FeatureJoiner_10
    ATTR_CONFLICT_RES = Use Left
    GEOMETRY_HANDLING = Use Left
    JOIN_KEYS = max_x max_x AUTO
    JOIN_MODE = Inner
    JOINED -> FeatureJoiner_11 [LEFT]
    UNJOINED_LEFT -> AttributeManager_55
AttributeManager_55
    ATTR_TABLE:
      SET_TO url7 = @Value(url1)
      SET_TO url8 = @Value(url1)
    -> AttributeManager_55_:_Output (output)
AttributeManager_55_:_Output (output)
FeatureJoiner_11
    ATTR_CONFLICT_RES = Use Left
    GEOMETRY_HANDLING = Use Left
    JOIN_KEYS = max_x max_x AUTO
    JOIN_MODE = Inner
    UNJOINED_LEFT -> AttributeManager_56
AttributeManager_56
    ATTR_TABLE = SET_TO url8 = @Value(url1)
    -> AttributeManager_56_:_Output (output)
AttributeManager_56_:_Output (output)

FME custom transformer Joiner_custom

Parameters:
- LAT_DEG_TILE =
- LAT_DEG_TILE_B =
- LON_DEG_TILE =
- XTILE =
- YTILE =
- ZOOM =

WorkspaceRunner_2_Input (input)
    -> Counter
Counter
    CNT_ATTR = _count
    DOMAIN = counter
    SCOPE = Global
    START = 0
    -> TestFilter
TestFilter
    DEFAULT_VALUE = <UNFILTERED>
    TEST_LIST = "BOOL_OP,OR,COMPOSITE_TEST,""""""1"""""",TEST_CLAUSE,TEST @Value(_count) = 0",1,"BOOL_OP,OR,COMPOSITE_TEST,""""""1"""""",TEST_CLAUSE,TEST @Value(_count) = 1",2,"BOOL_OP,OR,COMPOSITE_TEST,""""""1"""""",TEST_CLAUSE,TEST @Value(_count) = 2",3,"BOOL_OP,OR,COMPOSITE_TEST,""""""1"""""",TEST_CLAUSE,TEST @Value(_count) = 3",4,"BOOL_OP,OR,COMPOSITE_TEST,""""""1"""""",TEST_CLAUSE,TEST @Value(_count) = 4",5,"BOOL_OP,OR,COMPOSITE_TEST,""""""1"""""",TEST_CLAUSE,TEST @Value(_count) = 5",6,"BOOL_OP,OR,COMPOSITE_TEST,""""""1"""""",TEST_CLAUSE,TEST @Value(_count) = 6",7,"BOOL_OP,OR,COMPOSITE_TEST,""""""1"""""",TEST_CLAUSE,TEST @Value(_count) = 7",8,"BOOL_OP,OR,COMPOSITE_TEST,""""""1"""""",TEST_CLAUSE,TEST @Value(_count) = 8",9,"BOOL_OP,OR,COMPOSITE_TEST,""""""1"""""",TEST_CLAUSE,TEST @Value(_count) = 9",10,"BOOL_OP,OR,COMPOSITE_TEST,""""""1"""""",TEST_CLAUSE,TEST @Value(_count) = 10",11,"BOOL_OP,OR,COMPOSITE_TEST,""""""1"""""",TEST_CLAUSE,TEST @Value(_count) = 11",12,"BOOL_OP,OR,COMPOSITE_TEST,""""""1"""""",TEST_CLAUSE,TEST @Value(_count) = 12",13,"BOOL_OP,OR,COMPOSITE_TEST,""""""1"""""",TEST_CLAUSE,TEST @Value(_count) = 13",14,"BOOL_OP,OR,COMPOSITE_TEST,""""""1"""""",TEST_CLAUSE,TEST @Value(_count) = 14",15,"BOOL_OP,OR,COMPOSITE_TEST,""""""1"""""",TEST_CLAUSE,TEST @Value(_count) = 15",16,"BOOL_OP,OR,COMPOSITE_TEST,""""""1"""""",TEST_CLAUSE,TEST @Value(_count) = 16",17,"BOOL_OP,OR,COMPOSITE_TEST,""""""1"""""",TEST_CLAUSE,TEST @Value(_count) = 17",18,"BOOL_OP,OR,COMPOSITE_TEST,""""""1"""""",TEST_CLAUSE,TEST @Value(_count) = 18",19,"BOOL_OP,OR,COMPOSITE_TEST,""""""1"""""",TEST_CLAUSE,TEST @Value(_count) = 19",20,"BOOL_OP,OR,COMPOSITE_TEST,""""""1"""""",TEST_CLAUSE,TEST @Value(_count) = 20",21,"BOOL_OP,OR,COMPOSITE_TEST,""""""1"""""",TEST_CLAUSE,TEST @Value(_count) = 21",22,"BOOL_OP,OR,COMPOSITE_TEST,""""""1"""""",TEST_CLAUSE,TEST @Value(_count) = 22",23,"BOOL_OP,OR,COMPOSITE_TEST,""""""1"""""",TEST_CLAUSE,TEST @Value(_count) = 23",24,"BOOL_OP,OR,COMPOSITE_TEST,""""""1"""""",TEST_CLAUSE,TEST @Value(_count) = 24",25
    1 -> AttributeManager
    2 -> AttributeManager_2
    3 -> AttributeManager_3
    4 -> AttributeManager_4
    5 -> AttributeManager_5
    6 -> AttributeManager_6
    7 -> AttributeManager_7
    8 -> AttributeManager_8
    9 -> AttributeManager_9
    10 -> AttributeManager_10
    11 -> AttributeManager_11
    12 -> AttributeManager_12
    13 -> AttributeManager_13
    14 -> AttributeManager_14
    15 -> AttributeManager_15
    16 -> AttributeManager_16
    17 -> AttributeManager_17
    18 -> AttributeManager_18
    19 -> AttributeManager_19
    20 -> AttributeManager_20
    21 -> AttributeManager_21
    22 -> AttributeManager_22
    23 -> AttributeManager_23
    24 -> AttributeManager_24
    25 -> AttributeManager_25
AttributeManager
    ATTR_TABLE:
      RENAME_SET_VALUE lat_deg_tile > lat_deg_tile1
      RENAME_SET_VALUE lon_deg_tile > lon_deg_tile1
      RENAME_SET_VALUE xtile > xtile1
      RENAME_SET_VALUE ytile > ytile1
      SET_TO join = 0
      RENAME_SET_VALUE lat_deg_tile_b > lat_deg_tile_b1
    -> FeatureJoiner [LEFT]
AttributeManager_2
    ATTR_TABLE:
      RENAME_SET_VALUE lat_deg_tile > lat_deg_tile2
      RENAME_SET_VALUE lon_deg_tile > lon_deg_tile2
      RENAME_SET_VALUE xtile > xtile2
      RENAME_SET_VALUE ytile > ytile2
      SET_TO join = 0
      RENAME_SET_VALUE lat_deg_tile_b > lat_deg_tile_b2
    -> FeatureJoiner [RIGHT]
FeatureJoiner
    ATTR_CONFLICT_RES = Use Left
    GEOMETRY_HANDLING = Use Left
    JOIN_KEYS = join join AUTO
    JOIN_MODE = Full
    JOINED -> FeatureJoiner_2 [LEFT]
AttributeManager_3
    ATTR_TABLE:
      RENAME_SET_VALUE lat_deg_tile > lat_deg_tile3
      RENAME_SET_VALUE lon_deg_tile > lon_deg_tile3
      RENAME_SET_VALUE xtile > xtile3
      RENAME_SET_VALUE ytile > ytile3
      SET_TO join = 0
      RENAME_SET_VALUE lat_deg_tile_b > lat_deg_tile_b3
    -> FeatureJoiner_2 [RIGHT]
FeatureJoiner_2
    ATTR_CONFLICT_RES = Use Left
    GEOMETRY_HANDLING = Use Left
    JOIN_KEYS = join join AUTO
    JOIN_MODE = Full
    JOINED -> FeatureJoiner_3 [LEFT]
AttributeManager_4
    ATTR_TABLE:
      RENAME_SET_VALUE lat_deg_tile > lat_deg_tile4
      RENAME_SET_VALUE lon_deg_tile > lon_deg_tile4
      RENAME_SET_VALUE xtile > xtile4
      RENAME_SET_VALUE ytile > ytile4
      SET_TO join = 0
      RENAME_SET_VALUE lat_deg_tile_b > lat_deg_tile_b4
    -> FeatureJoiner_3 [RIGHT]
FeatureJoiner_3
    ATTR_CONFLICT_RES = Use Left
    GEOMETRY_HANDLING = Use Left
    JOIN_KEYS = join join AUTO
    JOIN_MODE = Full
    JOINED -> FeatureJoiner_4 [LEFT]
AttributeManager_5
    ATTR_TABLE:
      RENAME_SET_VALUE lat_deg_tile > lat_deg_tile5
      RENAME_SET_VALUE lon_deg_tile > lon_deg_tile5
      RENAME_SET_VALUE xtile > xtile5
      RENAME_SET_VALUE ytile > ytile5
      SET_TO join = 0
      RENAME_SET_VALUE lat_deg_tile_b > lat_deg_tile_b5
    -> FeatureJoiner_4 [RIGHT]
FeatureJoiner_4
    ATTR_CONFLICT_RES = Use Left
    GEOMETRY_HANDLING = Use Left
    JOIN_KEYS = join join AUTO
    JOIN_MODE = Full
    JOINED -> FeatureJoiner_5 [LEFT]
AttributeManager_6
    ATTR_TABLE:
      RENAME_SET_VALUE lat_deg_tile > lat_deg_tile6
      RENAME_SET_VALUE lon_deg_tile > lon_deg_tile6
      RENAME_SET_VALUE xtile > xtile6
      RENAME_SET_VALUE ytile > ytile6
      SET_TO join = 0
      RENAME_SET_VALUE lat_deg_tile_b > lat_deg_tile_b6
    -> FeatureJoiner_5 [RIGHT]
FeatureJoiner_5
    ATTR_CONFLICT_RES = Use Left
    GEOMETRY_HANDLING = Use Left
    JOIN_KEYS = join join AUTO
    JOIN_MODE = Full
    JOINED -> FeatureJoiner_6 [LEFT]
AttributeManager_7
    ATTR_TABLE:
      RENAME_SET_VALUE lat_deg_tile > lat_deg_tile7
      RENAME_SET_VALUE lon_deg_tile > lon_deg_tile7
      RENAME_SET_VALUE xtile > xtile7
      RENAME_SET_VALUE ytile > ytile7
      SET_TO join = 0
      RENAME_SET_VALUE lat_deg_tile_b > lat_deg_tile_b7
    -> FeatureJoiner_6 [RIGHT]
FeatureJoiner_6
    ATTR_CONFLICT_RES = Use Left
    GEOMETRY_HANDLING = Use Left
    JOIN_KEYS = join join AUTO
    JOIN_MODE = Full
    JOINED -> FeatureJoiner_7 [LEFT]
AttributeManager_8
    ATTR_TABLE:
      RENAME_SET_VALUE lat_deg_tile > lat_deg_tile8
      RENAME_SET_VALUE lon_deg_tile > lon_deg_tile8
      RENAME_SET_VALUE xtile > xtile8
      RENAME_SET_VALUE ytile > ytile8
      SET_TO join = 0
      RENAME_SET_VALUE lat_deg_tile_b > lat_deg_tile_b8
    -> FeatureJoiner_7 [RIGHT]
FeatureJoiner_7
    ATTR_CONFLICT_RES = Use Left
    GEOMETRY_HANDLING = Use Left
    JOIN_KEYS = join join AUTO
    JOIN_MODE = Full
    JOINED -> FeatureJoiner_8 [LEFT]
AttributeManager_9
    ATTR_TABLE:
      RENAME_SET_VALUE lat_deg_tile > lat_deg_tile9
      RENAME_SET_VALUE lon_deg_tile > lon_deg_tile9
      RENAME_SET_VALUE xtile > xtile9
      RENAME_SET_VALUE ytile > ytile9
      SET_TO join = 0
      RENAME_SET_VALUE lat_deg_tile_b > lat_deg_tile_b9
    -> FeatureJoiner_8 [RIGHT]
FeatureJoiner_8
    ATTR_CONFLICT_RES = Use Left
    GEOMETRY_HANDLING = Use Left
    JOIN_KEYS = join join AUTO
    JOIN_MODE = Full
    JOINED -> FeatureJoiner_9 [LEFT]
AttributeManager_10
    ATTR_TABLE:
      RENAME_SET_VALUE lat_deg_tile > lat_deg_tile10
      RENAME_SET_VALUE lon_deg_tile > lon_deg_tile10
      RENAME_SET_VALUE xtile > xtile10
      RENAME_SET_VALUE ytile > ytile10
      SET_TO join = 0
      RENAME_SET_VALUE lat_deg_tile_b > lat_deg_tile_b10
    -> FeatureJoiner_9 [RIGHT]
FeatureJoiner_9
    ATTR_CONFLICT_RES = Use Left
    GEOMETRY_HANDLING = Use Left
    JOIN_KEYS = join join AUTO
    JOIN_MODE = Full
    JOINED -> FeatureJoiner_10 [LEFT]
AttributeManager_11
    ATTR_TABLE:
      RENAME_SET_VALUE lat_deg_tile > lat_deg_tile11
      RENAME_SET_VALUE lon_deg_tile > lon_deg_tile11
      RENAME_SET_VALUE xtile > xtile11
      RENAME_SET_VALUE ytile > ytile11
      SET_TO join = 0
      RENAME_SET_VALUE lat_deg_tile_b > lat_deg_tile_b11
    -> FeatureJoiner_10 [RIGHT]
FeatureJoiner_10
    ATTR_CONFLICT_RES = Use Left
    GEOMETRY_HANDLING = Use Left
    JOIN_KEYS = join join AUTO
    JOIN_MODE = Full
    JOINED -> FeatureJoiner_11 [LEFT]
AttributeManager_12
    ATTR_TABLE:
      RENAME_SET_VALUE lat_deg_tile > lat_deg_tile12
      RENAME_SET_VALUE lon_deg_tile > lon_deg_tile12
      RENAME_SET_VALUE xtile > xtile12
      RENAME_SET_VALUE ytile > ytile12
      SET_TO join = 0
      RENAME_SET_VALUE lat_deg_tile_b > lat_deg_tile_b12
    -> FeatureJoiner_11 [RIGHT]
FeatureJoiner_11
    ATTR_CONFLICT_RES = Use Left
    GEOMETRY_HANDLING = Use Left
    JOIN_KEYS = join join AUTO
    JOIN_MODE = Full
    JOINED -> FeatureJoiner_12 [LEFT]
AttributeManager_13
    ATTR_TABLE:
      RENAME_SET_VALUE lat_deg_tile > lat_deg_tile13
      RENAME_SET_VALUE lon_deg_tile > lon_deg_tile13
      RENAME_SET_VALUE xtile > xtile13
      RENAME_SET_VALUE ytile > ytile13
      SET_TO join = 0
      RENAME_SET_VALUE lat_deg_tile_b > lat_deg_tile_b13
    -> FeatureJoiner_12 [RIGHT]
FeatureJoiner_12
    ATTR_CONFLICT_RES = Use Left
    GEOMETRY_HANDLING = Use Left
    JOIN_KEYS = join join AUTO
    JOIN_MODE = Full
    JOINED -> FeatureJoiner_13 [LEFT]
AttributeManager_14
    ATTR_TABLE:
      RENAME_SET_VALUE lat_deg_tile > lat_deg_tile14
      RENAME_SET_VALUE lon_deg_tile > lon_deg_tile14
      RENAME_SET_VALUE xtile > xtile14
      RENAME_SET_VALUE ytile > ytile14
      SET_TO join = 0
      RENAME_SET_VALUE lat_deg_tile_b > lat_deg_tile_b14
    -> FeatureJoiner_13 [RIGHT]
FeatureJoiner_13
    ATTR_CONFLICT_RES = Use Left
    GEOMETRY_HANDLING = Use Left
    JOIN_KEYS = join join AUTO
    JOIN_MODE = Full
    JOINED -> FeatureJoiner_14 [LEFT]
AttributeManager_15
    ATTR_TABLE:
      RENAME_SET_VALUE lat_deg_tile > lat_deg_tile15
      RENAME_SET_VALUE lon_deg_tile > lon_deg_tile15
      RENAME_SET_VALUE xtile > xtile15
      RENAME_SET_VALUE ytile > ytile15
      SET_TO join = 0
      RENAME_SET_VALUE lat_deg_tile_b > lat_deg_tile_b15
    -> FeatureJoiner_14 [RIGHT]
FeatureJoiner_14
    ATTR_CONFLICT_RES = Use Left
    GEOMETRY_HANDLING = Use Left
    JOIN_KEYS = join join AUTO
    JOIN_MODE = Full
    JOINED -> FeatureJoiner_15 [LEFT]
AttributeManager_16
    ATTR_TABLE:
      RENAME_SET_VALUE lat_deg_tile > lat_deg_tile16
      RENAME_SET_VALUE lon_deg_tile > lon_deg_tile16
      RENAME_SET_VALUE xtile > xtile16
      RENAME_SET_VALUE ytile > ytile16
      SET_TO join = 0
      RENAME_SET_VALUE lat_deg_tile_b > lat_deg_tile_b16
    -> FeatureJoiner_15 [RIGHT]
FeatureJoiner_15
    ATTR_CONFLICT_RES = Use Left
    GEOMETRY_HANDLING = Use Left
    JOIN_KEYS = join join AUTO
    JOIN_MODE = Full
    JOINED -> FeatureJoiner_16 [LEFT]
AttributeManager_17
    ATTR_TABLE:
      RENAME_SET_VALUE lat_deg_tile > lat_deg_tile17
      RENAME_SET_VALUE lon_deg_tile > lon_deg_tile17
      RENAME_SET_VALUE xtile > xtile17
      RENAME_SET_VALUE ytile > ytile17
      SET_TO join = 0
      RENAME_SET_VALUE lat_deg_tile_b > lat_deg_tile_b17
    -> FeatureJoiner_16 [RIGHT]
FeatureJoiner_16
    ATTR_CONFLICT_RES = Use Left
    GEOMETRY_HANDLING = Use Left
    JOIN_KEYS = join join AUTO
    JOIN_MODE = Full
    JOINED -> FeatureJoiner_17 [LEFT]
AttributeManager_18
    ATTR_TABLE:
      RENAME_SET_VALUE lat_deg_tile > lat_deg_tile18
      RENAME_SET_VALUE lon_deg_tile > lon_deg_tile18
      RENAME_SET_VALUE xtile > xtile18
      RENAME_SET_VALUE ytile > ytile18
      SET_TO join = 0
      RENAME_SET_VALUE lat_deg_tile_b > lat_deg_tile_b18
    -> FeatureJoiner_17 [RIGHT]
FeatureJoiner_17
    ATTR_CONFLICT_RES = Use Left
    GEOMETRY_HANDLING = Use Left
    JOIN_KEYS = join join AUTO
    JOIN_MODE = Full
    JOINED -> FeatureJoiner_18 [LEFT]
AttributeManager_19
    ATTR_TABLE:
      RENAME_SET_VALUE lat_deg_tile > lat_deg_tile19
      RENAME_SET_VALUE lon_deg_tile > lon_deg_tile19
      RENAME_SET_VALUE xtile > xtile19
      RENAME_SET_VALUE ytile > ytile19
      SET_TO join = 0
      RENAME_SET_VALUE lat_deg_tile_b > lat_deg_tile_b19
    -> FeatureJoiner_18 [RIGHT]
FeatureJoiner_18
    ATTR_CONFLICT_RES = Use Left
    GEOMETRY_HANDLING = Use Left
    JOIN_KEYS = join join AUTO
    JOIN_MODE = Full
    JOINED -> FeatureJoiner_19 [LEFT]
AttributeManager_20
    ATTR_TABLE:
      RENAME_SET_VALUE lat_deg_tile > lat_deg_tile20
      RENAME_SET_VALUE lon_deg_tile > lon_deg_tile20
      RENAME_SET_VALUE xtile > xtile20
      RENAME_SET_VALUE ytile > ytile20
      SET_TO join = 0
      RENAME_SET_VALUE lat_deg_tile_b > lat_deg_tile_b20
    -> FeatureJoiner_19 [RIGHT]
FeatureJoiner_19
    ATTR_CONFLICT_RES = Use Left
    GEOMETRY_HANDLING = Use Left
    JOIN_KEYS = join join AUTO
    JOIN_MODE = Full
    JOINED -> FeatureJoiner_20 [LEFT]
AttributeManager_21
    ATTR_TABLE:
      RENAME_SET_VALUE lat_deg_tile > lat_deg_tile21
      RENAME_SET_VALUE lon_deg_tile > lon_deg_tile21
      RENAME_SET_VALUE xtile > xtile21
      RENAME_SET_VALUE ytile > ytile21
      SET_TO join = 0
      RENAME_SET_VALUE lat_deg_tile_b > lat_deg_tile_b21
    -> FeatureJoiner_20 [RIGHT]
FeatureJoiner_20
    ATTR_CONFLICT_RES = Use Left
    GEOMETRY_HANDLING = Use Left
    JOIN_KEYS = join join AUTO
    JOIN_MODE = Full
    JOINED -> FeatureJoiner_21 [LEFT]
AttributeManager_22
    ATTR_TABLE:
      RENAME_SET_VALUE lat_deg_tile > lat_deg_tile22
      RENAME_SET_VALUE lon_deg_tile > lon_deg_tile22
      RENAME_SET_VALUE xtile > xtile22
      RENAME_SET_VALUE ytile > ytile22
      SET_TO join = 0
      RENAME_SET_VALUE lat_deg_tile_b > lat_deg_tile_b22
    -> FeatureJoiner_21 [RIGHT]
FeatureJoiner_21
    ATTR_CONFLICT_RES = Use Left
    GEOMETRY_HANDLING = Use Left
    JOIN_KEYS = join join AUTO
    JOIN_MODE = Full
    JOINED -> FeatureJoiner_22 [LEFT]
AttributeManager_23
    ATTR_TABLE:
      RENAME_SET_VALUE lat_deg_tile > lat_deg_tile23
      RENAME_SET_VALUE lon_deg_tile > lon_deg_tile23
      RENAME_SET_VALUE xtile > xtile23
      RENAME_SET_VALUE ytile > ytile23
      SET_TO join = 0
      RENAME_SET_VALUE lat_deg_tile_b > lat_deg_tile_b23
    -> FeatureJoiner_22 [RIGHT]
FeatureJoiner_22
    ATTR_CONFLICT_RES = Use Left
    GEOMETRY_HANDLING = Use Left
    JOIN_KEYS = join join AUTO
    JOIN_MODE = Full
    JOINED -> FeatureJoiner_23 [LEFT]
AttributeManager_24
    ATTR_TABLE:
      RENAME_SET_VALUE lat_deg_tile > lat_deg_tile24
      RENAME_SET_VALUE lon_deg_tile > lon_deg_tile24
      RENAME_SET_VALUE xtile > xtile24
      RENAME_SET_VALUE ytile > ytile24
      SET_TO join = 0
      RENAME_SET_VALUE lat_deg_tile_b > lat_deg_tile_b24
    -> FeatureJoiner_23 [RIGHT]
FeatureJoiner_23
    ATTR_CONFLICT_RES = Use Left
    GEOMETRY_HANDLING = Use Left
    JOIN_KEYS = join join AUTO
    JOIN_MODE = Full
    JOINED -> FeatureJoiner_24 [LEFT]
AttributeManager_25
    ATTR_TABLE:
      RENAME_SET_VALUE lat_deg_tile > lat_deg_tile25
      RENAME_SET_VALUE lon_deg_tile > lon_deg_tile25
      RENAME_SET_VALUE xtile > xtile25
      RENAME_SET_VALUE ytile > ytile25
      SET_TO join = 0
      RENAME_SET_VALUE lat_deg_tile_b > lat_deg_tile_b25
    -> FeatureJoiner_24 [RIGHT]
FeatureJoiner_24
    ATTR_CONFLICT_RES = Use Left
    GEOMETRY_HANDLING = Use Left
    JOIN_KEYS = join join AUTO
    JOIN_MODE = Full
    JOINED -> Output (output)
Output (output)
