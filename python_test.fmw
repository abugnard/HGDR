FME workspace python_test.fmw

Parameters:
- SourceDataset_OSMPBF = https://download.geofabrik.de/europe/switzerland-latest.osm.pbf   # Source OSM PBF File(s)

Readers:
- OSMPBF_1: OSMPBF from $(SourceDataset_OSMPBF)

aerialway (reader OSMPBF_1)
    attributes: name string, aerialway string
aeroway (reader OSMPBF_1)
    attributes: name string, aeroway string
    -> Reprojector
amenity (reader OSMPBF_1)
    attributes: name string, amenity string
    -> Reprojector
barrier (reader OSMPBF_1)
    attributes: source string, barrier string
    -> Reprojector
boundary (reader OSMPBF_1)
    attributes: admin_level string, source string, name string, boundary string
    -> Reprojector
building (reader OSMPBF_1)
    attributes: source string, building string
    -> Reprojector
craft (reader OSMPBF_1)
    attributes: name string, addr:street string, addr:housenumber string, craft string
    -> Reprojector
emergency (reader OSMPBF_1)
    attributes: fire_hydrant:type string, fire_hydrant:diameter string, fire_hydrant:position string, emergency string
    -> Reprojector
geological (reader OSMPBF_1)
    attributes: natural string, type string, geological string
    -> Reprojector
highway (reader OSMPBF_1)
    attributes: name string, highway string
    -> Reprojector
historic (reader OSMPBF_1)
    attributes: name string, historic string
    -> Reprojector
landuse (reader OSMPBF_1)
    attributes: source string, landuse string
    -> Reprojector
leisure (reader OSMPBF_1)
    attributes: sport string, source string, leisure string
    -> Reprojector
man_made (reader OSMPBF_1)
    attributes: source string, man_made string
    -> Reprojector
military (reader OSMPBF_1)
    attributes: name string, building string, military string
    -> Reprojector
natural (reader OSMPBF_1)
    attributes: source string, natural string
    -> Reprojector
office (reader OSMPBF_1)
    attributes: name string, addr:street string, building string, office string
    -> Reprojector
place (reader OSMPBF_1)
    attributes: name string, source string, place string
    -> Reprojector
power (reader OSMPBF_1)
    attributes: source string, power string
    -> Reprojector
public_transport (reader OSMPBF_1)
    attributes: name string, bus string, highway string, public_transport string
    -> Reprojector
railway (reader OSMPBF_1)
    attributes: gauge string, electrified string, railway string
    -> Reprojector
route (reader OSMPBF_1)
    attributes: network string, type string, name string, ref string, route string
    -> Reprojector
shop (reader OSMPBF_1)
    attributes: name string, addr:street string, shop string
    -> Reprojector
sport (reader OSMPBF_1)
    attributes: leisure string, name string, sport string
    -> Reprojector
tourism (reader OSMPBF_1)
    attributes: name string, information string, tourism string
    -> Reprojector
unfiltered (reader OSMPBF_1)
    attributes: unfiltered string
    -> Reprojector
unknown (reader OSMPBF_1)
    attributes: unknown string
    -> Reprojector
waterway (reader OSMPBF_1)
    attributes: source string, waterway string
    -> Reprojector
Reprojector
    DEST = LL-WGS84
    INTERPOLATION_TYPE_NAME = Nearest Neighbor
    RASTER_CELL_SIZE = Preserve Cells
    RASTER_TOLERANCE = 0.0
    SOURCE = Read from feature
    REPROJECTED -> Clipper [CLIPPEE]
Creator
    GEOM = <?xml version="1.0" encoding="US_ASCII" standalone="no" ?><geometry><polygon><line><coord x="6.837358230602739" y="46.493358230602745"/><coord x="6.9026417693972615" y="46.493358230602745"/><coord x="6.9026417693972615" y="46.55864176939726"/><coord x="6.837358230602739" y="46.55864176939726"/><coord x="6.837358230602739" y="46.493358230602745"/></line></polygon></geometry>
    GEOMTYPE = Geometry Object
    NUM = 1
    CREATED -> CoordinateSystemSetter
CoordinateSystemSetter
    COORDSYS = LL-WGS84
    -> LengthCalculator
LengthCalculator
    DIM = 2
    LEN_ATTR = _length
    MULT = 1
    -> Bufferer
Bufferer
    ANGLE = 22.5
    CAP_STYLE = Arc
    CORNER_STYLE = Arc
    MODE = AREA
    OFFSET = "@Value(_length)*0.1 "
    OFFSET_UNITS = NONE
    PRECISION = APPROX
    BUFFERED -> Clipper [CLIPPER]
Clipper
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> Inspector
Inspector
