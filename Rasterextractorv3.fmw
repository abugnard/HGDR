FME workspace Rasterextractorv3.fmw
Title: Geospatial PDF - Cartographic Output

Parameters:
- zoom = 5
- x_1 = 18   # x tile number
- x_2 = 18   # x tile number
- x_3 = 18   # x tile number
- x_4 = 19   # x tile number
- x_5 = 19   # x tile number
- x_6 = 19   # x tile number
- x_7 = 20   # x tile number
- x_8 = 20   # x tile number
- x_9 = 20   # x tile number
- x_10 = 18   # x tile number
- x_11 = 18   # x tile number
- x_12 = 18   # x tile number
- x_13 = 18   # x tile number
- x_14 = 18   # x tile number
- x_15 = 18   # x tile number
- x_16 = 18   # x tile number
- x_17 = 18   # x tile number
- x_18 = 18   # x tile number
- x_19 = 18   # x tile number
- x_20 = 18   # x tile number
- x_21 = 18   # x tile number
- x_22 = 18   # x tile number
- x_23 = 18   # x tile number
- x_24 = 18   # x tile number
- x_25 = 18   # x tile number
- y_1 = 9   # y tile number
- y_2 = 10   # y tile number
- y_3 = 11   # y tile number
- y_4 = 9   # y tile number
- y_5 = 10   # y tile number
- y_6 = 11   # y tile number
- y_7 = 9   # y tile number
- y_8 = 10   # y tile number
- y_9 = 11   # y tile number
- y_10 = 9   # y tile number
- y_11 = 9   # y tile number
- y_12 = 9   # y tile number
- y_13 = 9   # y tile number
- y_14 = 9   # y tile number
- y_15 = 9   # y tile number
- y_16 = 9   # y tile number
- y_17 = 9   # y tile number
- y_18 = 9   # y tile number
- y_19 = 9   # y tile number
- y_20 = 9   # y tile number
- y_21 = 9   # y tile number
- y_22 = 9   # y tile number
- y_23 = 9   # y tile number
- y_24 = 9   # y tile number
- y_25 = 9   # y tile number
- x_deg_1 = 22.5   # longitude 
- x_deg_2 = 22.5   # longitude 
- x_deg_3 = 22.5   # longitude 
- x_deg_4 = 33.75   # longitude 
- x_deg_5 = 33.75   # longitude 
- x_deg_6 = 33.75   # longitude 
- x_deg_7 = 45.0   # longitude 
- x_deg_8 = 45.0   # longitude 
- x_deg_9 = 45.0   # longitude 
- x_deg_10 = 22.5   # longitude 
- x_deg_11 = 22.5   # longitude 
- x_deg_12 = 22.5   # longitude 
- x_deg_13 = 22.5   # longitude 
- x_deg_14 = 22.5   # longitude 
- x_deg_15 = 22.5   # longitude 
- x_deg_16 = 22.5   # longitude 
- x_deg_17 = 22.5   # longitude 
- x_deg_18 = 22.5   # longitude 
- x_deg_19 = 22.5   # longitude 
- x_deg_20 = 22.5   # longitude 
- x_deg_21 = 22.5   # longitude 
- x_deg_22 = 22.5   # longitude 
- x_deg_23 = 22.5   # longitude 
- x_deg_24 = 22.5   # longitude 
- x_deg_25 = 22.5   # longitude 
- y_deg_1 = 61.60639637138628   # latitude 
- y_deg_2 = 55.77657301866769   # latitude 
- y_deg_3 = 48.92249926375824   # latitude 
- y_deg_4 = 61.60639637138628   # latitude 
- y_deg_5 = 55.77657301866769   # latitude 
- y_deg_6 = 48.92249926375824   # latitude 
- y_deg_7 = 61.60639637138628   # latitude 
- y_deg_8 = 55.77657301866769   # latitude 
- y_deg_9 = 48.92249926375824   # latitude 
- y_deg_10 = 61.60639637138628   # latitude 
- y_deg_11 = 61.60639637138628   # latitude 
- y_deg_12 = 61.60639637138628   # latitude 
- y_deg_13 = 61.60639637138628   # latitude 
- y_deg_14 = 61.60639637138628   # latitude 
- y_deg_15 = 61.60639637138628   # latitude 
- y_deg_16 = 61.60639637138628   # latitude 
- y_deg_17 = 61.60639637138628   # latitude 
- y_deg_18 = 61.60639637138628   # latitude 
- y_deg_19 = 61.60639637138628   # latitude 
- y_deg_20 = 61.60639637138628   # latitude 
- y_deg_21 = 61.60639637138628   # latitude 
- y_deg_22 = 61.60639637138628   # latitude 
- y_deg_23 = 61.60639637138628   # latitude 
- y_deg_24 = 61.60639637138628   # latitude 
- y_deg_25 = 61.60639637138628   # latitude 
- y_deg_b_1 = 55.77657301866769   # latitude below 
- y_deg_b_2 = 48.92249926375824   # latitude below 
- y_deg_b_3 = 40.97989806962013   # latitude below 
- y_deg_b_4 = 55.77657301866769   # latitude below 
- y_deg_b_5 = 48.92249926375824   # latitude below 
- y_deg_b_6 = 40.97989806962013   # latitude below 
- y_deg_b_7 = 55.77657301866769   # latitude below 
- y_deg_b_8 = 48.92249926375824   # latitude below 
- y_deg_b_9 = 40.97989806962013   # latitude below 
- y_deg_b_10 = 55.77657301866769   # latitude below 
- y_deg_b_11 = 55.77657301866769   # latitude below 
- y_deg_b_12 = 55.77657301866769   # latitude below 
- y_deg_b_13 = 55.77657301866769   # latitude below 
- y_deg_b_14 = 55.77657301866769   # latitude below 
- y_deg_b_15 = 55.77657301866769   # latitude below 
- y_deg_b_16 = 55.77657301866769   # latitude below 
- y_deg_b_17 = 55.77657301866769   # latitude below 
- y_deg_b_18 = 55.77657301866769   # latitude below 
- y_deg_b_19 = 55.77657301866769   # latitude below 
- y_deg_b_20 = 55.77657301866769   # latitude below 
- y_deg_b_21 = 55.77657301866769   # latitude below 
- y_deg_b_22 = 55.77657301866769   # latitude below 
- y_deg_b_23 = 55.77657301866769   # latitude below 
- y_deg_b_24 = 55.77657301866769   # latitude below 
- y_deg_b_25 = 55.77657301866769   # latitude below 
- min_lon = 30.70431384767483   # bb min lon
- min_lat = 44.704313847674825   # bb min lat
- max_lon = 45.295686152325175   # bb max lon
- max_lat = 59.295686152325175   # bb max lat
- DestDataset_JPEG = $(FME_MF_DIR)outputPDF   # Destination JPEG Folder
- DestDataset_PNGRASTER = $(FME_MF_DIR)outputPDF   # Destination PNG (Portable Network Graphics) Folder
- BASEMAPE = https://a.tile.opentopomap.org   # URL of the basemap
- BASEMAPE_ext = .png   # extention of the basemap
- ISO_code = test_final3   # Iso code of the extract
- DestDataset_JPEG2000_3 = $(FME_MF_DIR)outputPDF\subtiles   # Destination JPEG 2000 Folder
- DestDataset_PNGRASTER_3 = $(FME_MF_DIR)outputPDF\subtiles   # Destination PNG (Portable Network Graphics) Folder
- DestDataset_JPEG_4 = $(FME_MF_DIR)outputPDF\subtiles   # Destination JPEG Folder
- DestDataset_JPEG2000 = $(FME_MF_DIR)outputPDF   # Destination JPEG 2000 Folder

Writers:
- JPEG_1: JPEG to $(DestDataset_JPEG)
- JPEG2000_1: JPEG2000 to $(DestDataset_JPEG2000)
- PNGRASTER_1: PNGRASTER to $(DestDataset_PNGRASTER)
- JPEG_2: JPEG to $(DestDataset_JPEG)
- JPEG2000_2: JPEG2000 to $(DestDataset_JPEG2000_3)
- PNGRASTER_2: PNGRASTER to $(DestDataset_PNGRASTER_3) in LL-WGS84
- JPEG_3: JPEG to $(DestDataset_JPEG_4) in LL-WGS84

Creator_1
    GEOMTYPE = Geometry Object
    NUM = 1
    CREATED -> Cloner
Cloner
    COPIES = 25
    COPYATT = _copynum
    COPY -> AttributeCreator
AttributeCreator
    ATTR_TABLE:
      SET_TO xtile = FME_CONDITIONAL:DEFAULT_VALUE'_FME_NO_OP_'BOOL_OP;OR;COMPOSITE_TEST;1;TEST @Value(_copynum) = 0'$(x_1)'BOOL_OP;OR;COMPOSITE_TEST;1;TEST @Value(_copynum) = 1'$(x_2)'BOOL_OP;OR;COMPOSITE_TEST;1;TEST @Value(_copynum) = 2'$(x_3)'BOOL_OP;OR;COMPOSITE_TEST;1;TEST @Value(_copynum) = 3'$(x_4)'BOOL_OP;OR;COMPOSITE_TEST;1;TEST @Value(_copynum) = 4'$(x_5)'BOOL_OP;OR;COMPOSITE_TEST;1;TEST @Value(_copynum) = 5'$(x_6)'BOOL_OP;OR;COMPOSITE_TEST;1;TEST @Value(_copynum) = 6'$(x_7)'BOOL_OP;OR;COMPOSITE_TEST;1;TEST @Value(_copynum) = 7'$(x_8)'BOOL_OP;OR;COMPOSITE_TEST;1;TEST @Value(_copynum) = 8'$(x_9)'BOOL_OP;OR;COMPOSITE_TEST;1;TEST @Value(_copynum) = 9'$(x_10)'BOOL_OP;OR;COMPOSITE_TEST;1;TEST @Value(_copynum) = 10'$(x_11)'BOOL_OP;OR;COMPOSITE_TEST;1;TEST @Value(_copynum) = 11'$(x_12)'BOOL_OP;OR;COMPOSITE_TEST;1;TEST @Value(_copynum) = 12'$(x_13)'BOOL_OP;OR;COMPOSITE_TEST;1;TEST @Value(_copynum) = 13'$(x_14)'BOOL_OP;OR;COMPOSITE_TEST;1;TEST @Value(_copynum) = 14'$(x_15)'BOOL_OP;OR;COMPOSITE_TEST;1;TEST @Value(_copynum) = 15'$(x_16)'BOOL_OP;OR;COMPOSITE_TEST;1;TEST @Value(_copynum) = 16'$(x_17)'BOOL_OP;OR;COMPOSITE_TEST;1;TEST @Value(_copynum) = 17'$(x_18)'BOOL_OP;OR;COMPOSITE_TEST;1;TEST @Value(_copynum) = 18'$(x_19)'BOOL_OP;OR;COMPOSITE_TEST;1;TEST @Value(_copynum) = 19'$(x_20)'BOOL_OP;OR;COMPOSITE_TEST;1;TEST @Value(_copynum) = 20'$(x_21)'BOOL_OP;OR;COMPOSITE_TEST;1;TEST @Value(_copynum) = 21'$(x_22)'BOOL_OP;OR;COMPOSITE_TEST;1;TEST @Value(_copynum) = 22'$(x_23)'BOOL_OP;OR;COMPOSITE_TEST;1;TEST @Value(_copynum) = 23'$(x_24)'BOOL_OP;OR;COMPOSITE_TEST;1;TEST @Value(_copynum) = 24'$(x_25)'FME_NUM_CONDITIONS26___
      SET_TO ytile = FME_CONDITIONAL:DEFAULT_VALUE'_FME_NO_OP_'BOOL_OP;OR;COMPOSITE_TEST;1;TEST @Value(_copynum) = 0'$(y_1)'BOOL_OP;OR;COMPOSITE_TEST;1;TEST @Value(_copynum) = 1'$(y_2)'BOOL_OP;OR;COMPOSITE_TEST;1;TEST @Value(_copynum) = 2'$(y_3)'BOOL_OP;OR;COMPOSITE_TEST;1;TEST @Value(_copynum) = 3'$(y_4)'BOOL_OP;OR;COMPOSITE_TEST;1;TEST @Value(_copynum) = 4'$(y_5)'BOOL_OP;OR;COMPOSITE_TEST;1;TEST @Value(_copynum) = 5'$(y_6)'BOOL_OP;OR;COMPOSITE_TEST;1;TEST @Value(_copynum) = 6'$(y_7)'BOOL_OP;OR;COMPOSITE_TEST;1;TEST @Value(_copynum) = 7'$(y_8)'BOOL_OP;OR;COMPOSITE_TEST;1;TEST @Value(_copynum) = 8'$(y_9)'BOOL_OP;OR;COMPOSITE_TEST;1;TEST @Value(_copynum) = 9'$(y_10)'BOOL_OP;OR;COMPOSITE_TEST;1;TEST @Value(_copynum) = 10'$(y_11)'BOOL_OP;OR;COMPOSITE_TEST;1;TEST @Value(_copynum) = 11'$(y_12)'BOOL_OP;OR;COMPOSITE_TEST;1;TEST @Value(_copynum) = 12'$(y_13)'BOOL_OP;OR;COMPOSITE_TEST;1;TEST @Value(_copynum) = 13'$(y_14)'BOOL_OP;OR;COMPOSITE_TEST;1;TEST @Value(_copynum) = 14'$(y_15)'BOOL_OP;OR;COMPOSITE_TEST;1;TEST @Value(_copynum) = 15'$(y_16)'BOOL_OP;OR;COMPOSITE_TEST;1;TEST @Value(_copynum) = 16'$(y_17)'BOOL_OP;OR;COMPOSITE_TEST;1;TEST @Value(_copynum) = 17'$(y_18)'BOOL_OP;OR;COMPOSITE_TEST;1;TEST @Value(_copynum) = 18'$(y_19)'BOOL_OP;OR;COMPOSITE_TEST;1;TEST @Value(_copynum) = 19'$(y_20)'BOOL_OP;OR;COMPOSITE_TEST;1;TEST @Value(_copynum) = 20'$(y_21)'BOOL_OP;OR;COMPOSITE_TEST;1;TEST @Value(_copynum) = 21'$(y_22)'BOOL_OP;OR;COMPOSITE_TEST;1;TEST @Value(_copynum) = 22'$(y_23)'BOOL_OP;OR;COMPOSITE_TEST;1;TEST @Value(_copynum) = 23'$(y_24)'BOOL_OP;OR;COMPOSITE_TEST;1;TEST @Value(_copynum) = 24'$(y_25)'FME_NUM_CONDITIONS26___
      SET_TO xcorner = FME_CONDITIONAL:DEFAULT_VALUE'_FME_NO_OP_'BOOL_OP;OR;COMPOSITE_TEST;1;TEST @Value(_copynum) = 0'$(x_deg_1)'BOOL_OP;OR;COMPOSITE_TEST;1;TEST @Value(_copynum) = 1'$(x_deg_2)'BOOL_OP;OR;COMPOSITE_TEST;1;TEST @Value(_copynum) = 2'$(x_deg_3)'BOOL_OP;OR;COMPOSITE_TEST;1;TEST @Value(_copynum) = 3'$(x_deg_4)'BOOL_OP;OR;COMPOSITE_TEST;1;TEST @Value(_copynum) = 4'$(x_deg_5)'BOOL_OP;OR;COMPOSITE_TEST;1;TEST @Value(_copynum) = 5'$(x_deg_6)'BOOL_OP;OR;COMPOSITE_TEST;1;TEST @Value(_copynum) = 6'$(x_deg_7)'BOOL_OP;OR;COMPOSITE_TEST;1;TEST @Value(_copynum) = 7'$(x_deg_8)'BOOL_OP;OR;COMPOSITE_TEST;1;TEST @Value(_copynum) = 8'$(x_deg_9)'BOOL_OP;OR;COMPOSITE_TEST;1;TEST @Value(_copynum) = 9'$(x_deg_10)'BOOL_OP;OR;COMPOSITE_TEST;1;TEST @Value(_copynum) = 10'$(x_deg_11)'BOOL_OP;OR;COMPOSITE_TEST;1;TEST @Value(_copynum) = 11'$(x_deg_12)'BOOL_OP;OR;COMPOSITE_TEST;1;TEST @Value(_copynum) = 12'$(x_deg_13)'BOOL_OP;OR;COMPOSITE_TEST;1;TEST @Value(_copynum) = 13'$(x_deg_14)'BOOL_OP;OR;COMPOSITE_TEST;1;TEST @Value(_copynum) = 14'$(x_deg_15)'BOOL_OP;OR;COMPOSITE_TEST;1;TEST @Value(_copynum) = 15'$(x_deg_16)'BOOL_OP;OR;COMPOSITE_TEST;1;TEST @Value(_copynum) = 16'$(x_deg_17)'BOOL_OP;OR;COMPOSITE_TEST;1;TEST @Value(_copynum) = 17'$(x_deg_18)'BOOL_OP;OR;COMPOSITE_TEST;1;TEST @Value(_copynum) = 18'$(x_deg_19)'BOOL_OP;OR;COMPOSITE_TEST;1;TEST @Value(_copynum) = 19'$(x_deg_20)'BOOL_OP;OR;COMPOSITE_TEST;1;TEST @Value(_copynum) = 20'$(x_deg_21)'BOOL_OP;OR;COMPOSITE_TEST;1;TEST @Value(_copynum) = 21'$(x_deg_22)'BOOL_OP;OR;COMPOSITE_TEST;1;TEST @Value(_copynum) = 22'$(x_deg_23)'BOOL_OP;OR;COMPOSITE_TEST;1;TEST @Value(_copynum) = 23'$(x_deg_24)'BOOL_OP;OR;COMPOSITE_TEST;1;TEST @Value(_copynum) = 24'$(x_deg_25)'FME_NUM_CONDITIONS26___
      SET_TO ycorner = FME_CONDITIONAL:DEFAULT_VALUE'_FME_NO_OP_'BOOL_OP;OR;COMPOSITE_TEST;1;TEST @Value(_copynum) = 0'$(y_deg_1)'BOOL_OP;OR;COMPOSITE_TEST;1;TEST @Value(_copynum) = 1'$(y_deg_2)'BOOL_OP;OR;COMPOSITE_TEST;1;TEST @Value(_copynum) = 2'$(y_deg_3)'BOOL_OP;OR;COMPOSITE_TEST;1;TEST @Value(_copynum) = 3'$(y_deg_4)'BOOL_OP;OR;COMPOSITE_TEST;1;TEST @Value(_copynum) = 4'$(y_deg_5)'BOOL_OP;OR;COMPOSITE_TEST;1;TEST @Value(_copynum) = 5'$(y_deg_6)'BOOL_OP;OR;COMPOSITE_TEST;1;TEST @Value(_copynum) = 6'$(y_deg_7)'BOOL_OP;OR;COMPOSITE_TEST;1;TEST @Value(_copynum) = 7'$(y_deg_8)'BOOL_OP;OR;COMPOSITE_TEST;1;TEST @Value(_copynum) = 8'$(y_deg_9)'BOOL_OP;OR;COMPOSITE_TEST;1;TEST @Value(_copynum) = 9'$(y_deg_10)'BOOL_OP;OR;COMPOSITE_TEST;1;TEST @Value(_copynum) = 10'$(y_deg_11)'BOOL_OP;OR;COMPOSITE_TEST;1;TEST @Value(_copynum) = 11'$(y_deg_12)'BOOL_OP;OR;COMPOSITE_TEST;1;TEST @Value(_copynum) = 12'$(y_deg_13)'BOOL_OP;OR;COMPOSITE_TEST;1;TEST @Value(_copynum) = 13'$(y_deg_14)'BOOL_OP;OR;COMPOSITE_TEST;1;TEST @Value(_copynum) = 14'$(y_deg_15)'BOOL_OP;OR;COMPOSITE_TEST;1;TEST @Value(_copynum) = 15'$(y_deg_16)'BOOL_OP;OR;COMPOSITE_TEST;1;TEST @Value(_copynum) = 16'$(y_deg_17)'BOOL_OP;OR;COMPOSITE_TEST;1;TEST @Value(_copynum) = 17'$(y_deg_18)'BOOL_OP;OR;COMPOSITE_TEST;1;TEST @Value(_copynum) = 18'$(y_deg_19)'BOOL_OP;OR;COMPOSITE_TEST;1;TEST @Value(_copynum) = 19'$(y_deg_20)'BOOL_OP;OR;COMPOSITE_TEST;1;TEST @Value(_copynum) = 20'$(y_deg_21)'BOOL_OP;OR;COMPOSITE_TEST;1;TEST @Value(_copynum) = 21'$(y_deg_22)'BOOL_OP;OR;COMPOSITE_TEST;1;TEST @Value(_copynum) = 22'$(y_deg_23)'BOOL_OP;OR;COMPOSITE_TEST;1;TEST @Value(_copynum) = 23'$(y_deg_24)'BOOL_OP;OR;COMPOSITE_TEST;1;TEST @Value(_copynum) = 24'$(y_deg_25)'FME_NUM_CONDITIONS26___
      SET_TO ycorner_b = FME_CONDITIONAL:DEFAULT_VALUE'_FME_NO_OP_'BOOL_OP;OR;COMPOSITE_TEST;1;TEST @Value(_copynum) = 0'$(y_deg_b_1)'BOOL_OP;OR;COMPOSITE_TEST;1;TEST @Value(_copynum) = 1'$(y_deg_b_2)'BOOL_OP;OR;COMPOSITE_TEST;1;TEST @Value(_copynum) = 2'$(y_deg_b_3)'BOOL_OP;OR;COMPOSITE_TEST;1;TEST @Value(_copynum) = 3'$(y_deg_b_4)'BOOL_OP;OR;COMPOSITE_TEST;1;TEST @Value(_copynum) = 4'$(y_deg_b_5)'BOOL_OP;OR;COMPOSITE_TEST;1;TEST @Value(_copynum) = 5'$(y_deg_b_6)'BOOL_OP;OR;COMPOSITE_TEST;1;TEST @Value(_copynum) = 6'$(y_deg_b_7)'BOOL_OP;OR;COMPOSITE_TEST;1;TEST @Value(_copynum) = 7'$(y_deg_b_8)'BOOL_OP;OR;COMPOSITE_TEST;1;TEST @Value(_copynum) = 8'$(y_deg_b_9)'BOOL_OP;OR;COMPOSITE_TEST;1;TEST @Value(_copynum) = 9'$(y_deg_b_10)'BOOL_OP;OR;COMPOSITE_TEST;1;TEST @Value(_copynum) = 10'$(y_deg_b_11)'BOOL_OP;OR;COMPOSITE_TEST;1;TEST @Value(_copynum) = 11'$(y_deg_b_12)'BOOL_OP;OR;COMPOSITE_TEST;1;TEST @Value(_copynum) = 12'$(y_deg_b_13)'BOOL_OP;OR;COMPOSITE_TEST;1;TEST @Value(_copynum) = 13'$(y_deg_b_14)'BOOL_OP;OR;COMPOSITE_TEST;1;TEST @Value(_copynum) = 14'$(y_deg_b_15)'BOOL_OP;OR;COMPOSITE_TEST;1;TEST @Value(_copynum) = 15'$(y_deg_b_16)'BOOL_OP;OR;COMPOSITE_TEST;1;TEST @Value(_copynum) = 16'$(y_deg_b_17)'BOOL_OP;OR;COMPOSITE_TEST;1;TEST @Value(_copynum) = 17'$(y_deg_b_18)'BOOL_OP;OR;COMPOSITE_TEST;1;TEST @Value(_copynum) = 18'$(y_deg_b_19)'BOOL_OP;OR;COMPOSITE_TEST;1;TEST @Value(_copynum) = 19'$(y_deg_b_20)'BOOL_OP;OR;COMPOSITE_TEST;1;TEST @Value(_copynum) = 20'$(y_deg_b_21)'BOOL_OP;OR;COMPOSITE_TEST;1;TEST @Value(_copynum) = 21'$(y_deg_b_22)'BOOL_OP;OR;COMPOSITE_TEST;1;TEST @Value(_copynum) = 22'$(y_deg_b_23)'BOOL_OP;OR;COMPOSITE_TEST;1;TEST @Value(_copynum) = 23'$(y_deg_b_24)'BOOL_OP;OR;COMPOSITE_TEST;1;TEST @Value(_copynum) = 24'$(y_deg_b_25)'FME_NUM_CONDITIONS26___
    -> AttributeManager
AttributeManager
    ATTR_TABLE:
      SET_TO UL_x = @Value(xcorner)
      SET_TO UL_y = @Value(ycorner)
      SET_TO UR_x = @Value(xcorner)+(360/@pow(2,$(zoom)))
      SET_TO UR_y = @Value(ycorner)
      SET_TO LL_x = @Value(xcorner)
      SET_TO LL_y = @Value(ycorner_b)
      SET_TO LR_x = @Value(xcorner)+(360/@pow(2,$(zoom)))
      SET_TO LR_y = @Value(ycorner_b)
    -> TestFilter
TestFilter
    DEFAULT_VALUE = delete
    TEST_LIST:
      "BOOL_OP,COMPOSITE,COMPOSITE_TEST,""""""( 1 OR 2 ) OR ( 3 )"""""",TEST_CLAUSE,TEST @Value(xtile) != $(x_1)
      TEST @Value(ytile) != $(y_1)
      TEST @Value(_copynum) = 0",pass
    pass -> TestFilter_17
TestFilter_17
    DEFAULT_VALUE = jpg
    TEST_LIST = "BOOL_OP,OR,COMPOSITE_TEST,""""""1"""""",TEST_CLAUSE,TEST $(BASEMAPE_ext) = .png",png
    png -> AttributeManager_2
    jpg -> TestFilter_2
AttributeManager_2
    ATTR_TABLE = SET_TO URL_BM = $(BASEMAPE)/$(zoom)
    -> AttributeCreator_2
AttributeCreator_2
    ATTR_TABLE = SET_TO url = @Value(URL_BM)/@Value(xtile)/@Value(ytile).png
    -> ImageFetcher
ImageFetcher
    CONNECTION_TIMEOUT_LENGTH = 60
    ERROR_ATTR = _http_error
    FOLLOW_REDIRECTS = Yes
    RASTER_TYPE = PNG
    RESPONSE_HEADER_LIST_ATTR = _http_headers
    STATUS_CODE_ATTR = _http_status_code
    TRANSFER_TIMEOUT_LENGTH = 90
    URL = @Value(url)
    USE_COOKIES = No
    VERIFY_SSL_CERTIFICATES = Yes
    RASTER -> CoordinateSystemSetter
CoordinateSystemSetter
    COORDSYS = LL-WGS84
    -> RasterPaletteResolver_10
RasterPaletteResolver_10
    -> RasterGeoreferencer_10
RasterGeoreferencer_10
    POINTANDANGLE_OR_EXTENTS = Extents
    X_LL_COORD = @Value(LL_x)
    X_LR_COORD = @Value(LR_x)
    X_UL_COORD = @Value(UL_x)
    X_UR_COORD = @Value(UR_x)
    Y_LL_COORD = @Value(LL_y)
    Y_LR_COORD = @Value(LR_y)
    Y_UL_COORD = @Value(UL_y)
    Y_UR_COORD = @Value(UR_y)
    -> RasterMosaicker
RasterMosaicker
    ACCUM_ATTRS_NAME = Use Attributes From One Feature
    INTERPOLATION_TYPE_NAME = Nearest Neighbor
    MERGE_PALETTES_NAME = Yes
    NODATA_OVERWRITE = No
    OVERLAPPING_VALUES = last
    SNAPPING_TYPE_NAME = Offset
    -> Clipper_2 [CLIPPEE]
TestFilter_2
    DEFAULT_VALUE = BLUEMARBLE
    TEST_LIST = "BOOL_OP,OR,COMPOSITE_TEST,""""""1"""""",TEST_CLAUSE,CASE_INSENSITIVE_TEST $(BASEMAPE) CONTAINS arcgisonline.com",ARCGIS
    ARCGIS -> AttributeManager_3
    BLUEMARBLE -> AttributeManager_4
AttributeManager_3
    ATTR_TABLE = SET_TO URL_BM = $(BASEMAPE)/$(zoom)
    -> AttributeCreator_3
AttributeCreator_3
    ATTR_TABLE = SET_TO url = @Value(URL_BM)/@Value(ytile)/@Value(xtile).jpg
    -> ImageFetcher_2
AttributeManager_4
    ATTR_TABLE = SET_TO URL_BM = $(BASEMAPE)/$(zoom)
    -> AttributeCreator_4
AttributeCreator_4
    ATTR_TABLE = SET_TO url = @Value(URL_BM)-r@Value(ytile)-c@Value(xtile).jpg
    -> ImageFetcher_2
ImageFetcher_2
    CONNECTION_TIMEOUT_LENGTH = 60
    ERROR_ATTR = _http_error
    FOLLOW_REDIRECTS = Yes
    RASTER_TYPE = <Auto-Detect from HTTP Headers>
    RESPONSE_HEADER_LIST_ATTR = _http_headers
    STATUS_CODE_ATTR = _http_status_code
    TRANSFER_TIMEOUT_LENGTH = 90
    URL = @Value(url)
    USE_COOKIES = No
    VERIFY_SSL_CERTIFICATES = Yes
    RASTER -> CoordinateSystemSetter_2
CoordinateSystemSetter_2
    COORDSYS = LL-WGS84
    -> RasterPaletteResolver_2
RasterPaletteResolver_2
    -> RasterGeoreferencer_2
RasterGeoreferencer_2
    POINTANDANGLE_OR_EXTENTS = Extents
    X_LL_COORD = @Value(LL_x)
    X_LR_COORD = @Value(LR_x)
    X_UL_COORD = @Value(UL_x)
    X_UR_COORD = @Value(UR_x)
    Y_LL_COORD = @Value(LL_y)
    Y_LR_COORD = @Value(LR_y)
    Y_UL_COORD = @Value(UL_y)
    Y_UR_COORD = @Value(UR_y)
    -> RasterMosaicker_2
RasterMosaicker_2
    ACCUM_ATTRS_NAME = Drop Incoming Attributes
    INTERPOLATION_TYPE_NAME = Nearest Neighbor
    MERGE_PALETTES_NAME = Yes
    NODATA_OVERWRITE = No
    OVERLAPPING_VALUES = last
    SNAPPING_TYPE_NAME = Offset
    -> Clipper_3 [CLIPPEE]
Creator_4
    COORDS = $(max_lon) $(max_lat) $(max_lon) $(min_lat) $(min_lon) $(min_lat) $(min_lon) $(max_lat) $(max_lon) $(max_lat)
    COORDSYS = LL-WGS84
    GEOMTYPE = 2D Coordinate List
    NUM = 1
    CREATED -> Clipper_2 [CLIPPER]
Clipper_2
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> Raster1 (writer PNGRASTER_1)
    INSIDE -> TestFilter_4
    INSIDE -> TestFilter_3
TestFilter_4
    DEFAULT_VALUE = <UNFILTERED>
    TEST_LIST = "BOOL_OP,OR,COMPOSITE_TEST,""""""1"""""",TEST_CLAUSE,CASE_INSENSITIVE_TEST @Value(url) CONTAINS toner",@Value(url) CONTAINS toner
    @Value(url) CONTAINS toner -> RasterSelector
    <UNFILTERED> -> JPEG200000 (writer JPEG2000_1)
    <UNFILTERED> -> Raster1 (writer JPEG_2)
RasterSelector
    BAND_LIST = 3:ALL
    SELECTION_MODE = Band and Palette List
    -> RasterBandRemover
RasterBandRemover
    -> Raster1 (writer JPEG_2)
    -> JPEG200000 (writer JPEG2000_1)
Raster1 (writer JPEG_2)
    attributes: _creation_instance decimal(20,0), url char(200), xtile char(200), ytile char(200), xcorner char(200), ycorner char(200), _copynum char(200), UL_x char(200), UL_y char(200), UR_x char(200), UR_y char(200), LL_x char(200), LL_y char(200), LR_x char(200), LR_y char(200), URL_BM char(200), ycorner_b char(200), _http_status_code char(200), _http_headers{}_name char(200), _http_headers{}_value char(200), _clipped char(200)
JPEG200000 (writer JPEG2000_1)
Raster1 (writer PNGRASTER_1)
    attributes: _creation_instance decimal(20,0), url char(200), xtile char(200), ytile char(200), xcorner char(200), ycorner char(200), _copynum char(200), UL_x char(200), UL_y char(200), UR_x char(200), UR_y char(200), LL_x char(200), LL_y char(200), LR_x char(200), LR_y char(200), URL_BM char(200), ycorner_b char(200), _http_status_code char(200), _http_headers{}_name char(200), _http_headers{}_value char(200), _clipped char(200)
TestFilter_3
    DEFAULT_VALUE = <UNFILTERED>
    TEST_LIST = "BOOL_OP,OR,COMPOSITE_TEST,""""""1"""""",TEST_CLAUSE,CASE_INSENSITIVE_TEST @Value(url) CONTAINS toner",@Value(url) CONTAINS toner
    @Value(url) CONTAINS toner -> RasterTiler
    <UNFILTERED> -> RasterTiler_3
RasterTiler_3
    FORCE_EQUAL_SIZED_TILES = No
    NUM_HORIZONTAL_TILES = 3
    NUM_HORIZONTAL_TILES_ATTRIBUTE = _num_tile_columns
    NUM_VERTICAL_TILES = 4
    NUM_VERTICAL_TILES_ATTRIBUTE = _num_tile_rows
    RASTER_INDEX_ATTRIBUTE = _raster_index
    TILESIZE_OR_NUMTILES = Number of Tiles
    TILE_COLUMN_ATTRIBUTE = _tile_column
    TILE_ROW_ATTRIBUTE = _tile_row
    TILES -> Raster1 (writer JPEG2000_2)
    TILES -> Raster1 (writer JPEG_3)
    TILES -> Raster101 (writer PNGRASTER_2)
Raster101 (writer PNGRASTER_2)
    attributes: _creation_instance decimal(20,0), url char(200), xtile char(200), ytile char(200), xcorner char(200), ycorner char(200), _copynum char(200), UL_x char(200), UL_y char(200), UR_x char(200), UR_y char(200), LL_x char(200), LL_y char(200), LR_x char(200), LR_y char(200), URL_BM char(200), ycorner_b char(200), _http_status_code char(200), _http_headers{}_name char(200), _http_headers{}_value char(200), _clipped char(200), _raster_index char(200), _tile_column char(200), _tile_row char(200), _num_tile_columns char(200), _num_tile_rows char(200)
RasterTiler
    FORCE_EQUAL_SIZED_TILES = No
    NUM_HORIZONTAL_TILES = 3
    NUM_HORIZONTAL_TILES_ATTRIBUTE = _num_tile_columns
    NUM_VERTICAL_TILES = 4
    NUM_VERTICAL_TILES_ATTRIBUTE = _num_tile_rows
    RASTER_INDEX_ATTRIBUTE = _raster_index
    TILESIZE_OR_NUMTILES = Number of Tiles
    TILE_COLUMN_ATTRIBUTE = _tile_column
    TILE_ROW_ATTRIBUTE = _tile_row
    TILES -> RasterSelector_2
RasterSelector_2
    BAND_LIST = 3:ALL
    SELECTION_MODE = Band and Palette List
    -> RasterBandRemover_2
RasterBandRemover_2
    -> Raster1 (writer JPEG2000_2)
    -> Raster1 (writer JPEG_3)
Raster1 (writer JPEG2000_2)
    attributes: _creation_instance decimal(20,0), url char(200), xtile char(200), ytile char(200), xcorner char(200), ycorner char(200), _copynum char(200), UL_x char(200), UL_y char(200), UR_x char(200), UR_y char(200), LL_x char(200), LL_y char(200), LR_x char(200), LR_y char(200), URL_BM char(200), ycorner_b char(200), _http_status_code char(200), _http_headers{}_name char(200), _http_headers{}_value char(200), _clipped char(200), _raster_index char(200), _tile_column char(200), _tile_row char(200), _num_tile_columns char(200), _num_tile_rows char(200)
Raster1 (writer JPEG_3)
    attributes: _creation_instance decimal(20,0), url char(200), xtile char(200), ytile char(200), xcorner char(200), ycorner char(200), _copynum char(200), UL_x char(200), UL_y char(200), UR_x char(200), UR_y char(200), LL_x char(200), LL_y char(200), LR_x char(200), LR_y char(200), URL_BM char(200), ycorner_b char(200), _http_status_code char(200), _http_headers{}_name char(200), _http_headers{}_value char(200), _clipped char(200), _raster_index char(200), _tile_column char(200), _tile_row char(200), _num_tile_columns char(200), _num_tile_rows char(200)
Creator_2
    COORDS = $(max_lon) $(max_lat) $(max_lon) $(min_lat) $(min_lon) $(min_lat) $(min_lon) $(max_lat) $(max_lon) $(max_lat)
    COORDSYS = LL-WGS84
    GEOMTYPE = 2D Coordinate List
    NUM = 1
    CREATED -> Clipper_3 [CLIPPER]
Clipper_3
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    INSIDE -> Raster100 (writer PNGRASTER_1)
    INSIDE -> RasterTiler_2
    INSIDE -> JPEG20000000 (writer JPEG2000_1)
    INSIDE -> Raster100 (writer JPEG_2)
JPEG20000000 (writer JPEG2000_1)
Raster100 (writer JPEG_2)
    attributes: _clipped char(200)
Raster100 (writer PNGRASTER_1)
    attributes: _clipped char(200)
RasterTiler_2
    FORCE_EQUAL_SIZED_TILES = No
    NUM_HORIZONTAL_TILES = 3
    NUM_HORIZONTAL_TILES_ATTRIBUTE = _num_tile_columns
    NUM_VERTICAL_TILES = 4
    NUM_VERTICAL_TILES_ATTRIBUTE = _num_tile_rows
    RASTER_INDEX_ATTRIBUTE = _raster_index
    TILESIZE_OR_NUMTILES = Number of Tiles
    TILE_COLUMN_ATTRIBUTE = _tile_column
    TILE_ROW_ATTRIBUTE = _tile_row
    TILES -> Raster100 (writer PNGRASTER_2)
    TILES -> Raster100 (writer JPEG_3)
    TILES -> Raster100 (writer JPEG2000_2)
Raster100 (writer PNGRASTER_2)
    attributes: _clipped char(200), _raster_index char(200), _tile_column char(200), _tile_row char(200), _num_tile_columns char(200), _num_tile_rows char(200)
Raster100 (writer JPEG2000_2)
    attributes: _clipped char(200), _raster_index char(200), _tile_column char(200), _tile_row char(200), _num_tile_columns char(200), _num_tile_rows char(200)
Raster100 (writer JPEG_3)
    attributes: _clipped char(200), _raster_index char(200), _tile_column char(200), _tile_row char(200), _num_tile_columns char(200), _num_tile_rows char(200)
