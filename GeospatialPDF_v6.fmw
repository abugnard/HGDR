FME workspace GeospatialPDF_v6.fmw

Parameters:
- FILE_name = Test.pdf   # Choose filename
- Tile_num = 0   # Part of the boundingbox
- SQUARE_SIZE_KM = 3.053482594705869   # Square size [km]
- Features_to_print = power waterway boundary emergency public_transport railway aerialway   # Features to put on PDF
- SourceDataset_JPEG2000 = $(FME_MF_DIR)output_CHE\05_PDF_export\basemap_CHE.jp2   # Source JPEG 2000 File(s)
- Number_of_features = 7   # Number of features
- Layer_feature = $(FME_MF_DIR)output   # Source of the layer to map
- DATE = 20220805   # Date 
- ISO = CHE   # ISO code
- SourceDataset_PDF2D = $(FME_MF_DIR)PDF_legend.pdf   # Source Adobe Geospatial PDF File
- GEOM = 6.87 46.51 6.91 46.55   # BoundingBox
- DEST_PDF = $(FME_MF_DIR)outputPDF   # Destination generated PDF
- LAYER_TYPE_2_MAP = OSM PopDens   # Choose the layer to put on PDF

Readers:
- JPEG2000_1: JPEG2000 from $(SourceDataset_JPEG2000) in LL-WGS84
- PDF2D_1: PDF2D from $(SourceDataset_PDF2D)

JPEG2000 (reader JPEG2000_1)
    -> BoundingBoxAccumulator
    -> AttributeCreator
BoundingBoxAccumulator
    ACCUM_ATTRS_NAME = Use Attributes From One Feature
    BOUNDING_BOX -> AttributeCreator_2
    BOUNDING_BOX -> Cloner_13
Cloner_13
    COPIES = @WordCount($(LAYER_TYPE_2_MAP))
    COPYATT = _copynum
    COPY -> AttributeManager_16
AttributeManager_16
    ATTR_TABLE = SET_TO Layer = @GetWord($(LAYER_TYPE_2_MAP),@Value(_copynum))
    -> TestFilter_8
TestFilter_8
    DEFAULT_VALUE = <UNFILTERED>
    TEST_LIST = "BOOL_OP,OR,COMPOSITE_TEST,""""""1"""""",TEST_CLAUSE,CASE_INSENSITIVE_TEST @Value(Layer) CONTAINS DEM",DEM,"BOOL_OP,OR,COMPOSITE_TEST,""""""1"""""",TEST_CLAUSE,CASE_INSENSITIVE_TEST @Value(Layer) CONTAINS OSM",OSM,"BOOL_OP,OR,COMPOSITE_TEST,""""""1"""""",TEST_CLAUSE,CASE_INSENSITIVE_TEST @Value(Layer) CONTAINS PopDens",PopDens,"BOOL_OP,OR,COMPOSITE_TEST,""""""1"""""",TEST_CLAUSE,CASE_INSENSITIVE_TEST @Value(Layer) CONTAINS ContourLines",ContourLines
    DEM -> FeatureReader_7 [INITIATOR]
    DEM -> Clipper_2 [CLIPPER]
    OSM -> Clipper_4 [CLIPPER]
    PopDens -> FeatureReader_9 [INITIATOR]
    PopDens -> Clipper_5 [CLIPPER]
    ContourLines -> FeatureReader_8 [INITIATOR]
    ContourLines -> Clipper_3 [CLIPPER]
Note: Sort drawing order with _order
Sorter
    SORT_PARM = _order NUMERIC ASCENDING
    SORTED -> PDFPageFormatter [Main]
Note: Set the page size and add 'Title', 'Main' and 'Signature' frames. / To control the feature type order in the output 'Layer', they must / be ordered by how they should be drawn using the sorter transformer. / NOTE: All feature types that overlap must be considered in the / same frame (drawing object) or the scale and bounds will not match.
PDFPageFormatter
    PAGE_HEIGHT_PTS = 612
    PAGE_HEIGHT_USER = 8.5
    PAGE_NUMBER = 1
    PAGE_OBJECTS = "DEM Scale SIZE_PARAMS;;MINX;573.133;SCALING_PARAMS;;CLIPPING_ENABLED;No;FIXED_ASPECT;Yes;MINY;69.4822;HEIGHT;14.4;WIDTH;201.6","Main SIZE_PARAMS;;MINX;13.6972;SCALING_PARAMS;;CLIPPING_ENABLED;No;FIXED_ASPECT;Yes;MINY;27.0021;HEIGHT;540;WIDTH;540","min SIZE_PARAMS;;MINX;563.76;SCALING_PARAMS;;CLIPPING_ENABLED;No;FIXED_ASPECT;Yes;MINY;52.56;HEIGHT;25.2;WIDTH;50.4","DEM Scale SIZE_PARAMS;;MINX;573.133;SCALING_PARAMS;;CLIPPING_ENABLED;No;FIXED_ASPECT;Yes;MINY;69.4822;HEIGHT;14.4;WIDTH;201.6","OSM SIZE_PARAMS;;MINX;554.4;SCALING_PARAMS;;CLIPPING_ENABLED;No;FIXED_ASPECT;Yes;MINY;470.88;HEIGHT;25.92;WIDTH;61.92","contour SIZE_PARAMS;;MINX;597.6;SCALING_PARAMS;;CLIPPING_ENABLED;No;FIXED_ASPECT;Yes;MINY;463.68;HEIGHT;25.92;WIDTH;94.32","Population Density SIZE_PARAMS;;MINX;697.68;SCALING_PARAMS;;CLIPPING_ENABLED;No;FIXED_ASPECT;Yes;MINY;461.52;HEIGHT;25.92;WIDTH;46.08","PF SIZE_PARAMS;;MINX;562.32;SCALING_PARAMS;;CLIPPING_ENABLED;No;FIXED_ASPECT;Yes;MINY;555.12;HEIGHT;25.92;WIDTH;144.72","Features_preview SIZE_PARAMS;;MINX;562.32;SCALING_PARAMS;;CLIPPING_ENABLED;No;FIXED_ASPECT;Yes;MINY;491.04;HEIGHT;63.36;WIDTH;187.2","Tf SIZE_PARAMS;;MINX;571.68;SCALING_PARAMS;;CLIPPING_ENABLED;No;FIXED_ASPECT;Yes;MINY;495.36;HEIGHT;63.36;WIDTH;193.68","Hide SIZE_PARAMS;;MINX;562.32;SCALING_PARAMS;;CLIPPING_ENABLED;No;FIXED_ASPECT;Yes;MINY;491.76;HEIGHT;63.36;WIDTH;187.2","Units SIZE_PARAMS;;MINX;587.52;SCALING_PARAMS;;CLIPPING_ENABLED;No;FIXED_ASPECT;Yes;MINY;149.04;HEIGHT;20.16;WIDTH;84.24","left_scale SIZE_PARAMS;;MINX;587.52;SCALING_PARAMS;;CLIPPING_ENABLED;No;FIXED_ASPECT;Yes;MINY;129.6;HEIGHT;21.6;WIDTH;68.4","right_scale SIZE_PARAMS;;MINX;655.92;SCALING_PARAMS;;CLIPPING_ENABLED;No;FIXED_ASPECT;Yes;MINY;129.6;HEIGHT;21.6;WIDTH;68.4","Scale 1 SIZE_PARAMS;;MINX;702;SCALING_PARAMS;;CLIPPING_ENABLED;No;FIXED_ASPECT;Yes;MINY;113.04;HEIGHT;14.4;WIDTH;36","Signature_Frame SIZE_PARAMS;;MINX;588.119;SCALING_PARAMS;;CLIPPING_ENABLED;No;FIXED_ASPECT;Yes;MINY;6.36556;HEIGHT;20;WIDTH;198","Title_Frame SIZE_PARAMS;;MINX;17.2456;SCALING_PARAMS;;CLIPPING_ENABLED;No;FIXED_ASPECT;Yes;MINY;578.035;HEIGHT;20;WIDTH;219.47","Scale 2 SIZE_PARAMS;;MINX;635.76;SCALING_PARAMS;;CLIPPING_ENABLED;No;FIXED_ASPECT;Yes;MINY;113.04;HEIGHT;14.4;WIDTH;36","Scale 3 SIZE_PARAMS;;MINX;568.08;SCALING_PARAMS;;CLIPPING_ENABLED;No;FIXED_ASPECT;Yes;MINY;113.04;HEIGHT;14.4;WIDTH;36","North SIZE_PARAMS;;MINX;648;SCALING_PARAMS;;CLIPPING_ENABLED;No;FIXED_ASPECT;Yes;MINY;244.8;HEIGHT;14.4;WIDTH;14.4","tabular SIZE_PARAMS;;MINX;587.52;SCALING_PARAMS;;CLIPPING_ENABLED;No;FIXED_ASPECT;Yes;MINY;265.68;HEIGHT;166.32;WIDTH;144.72","coord SIZE_PARAMS;;MINX;594.72;SCALING_PARAMS;;CLIPPING_ENABLED;No;FIXED_ASPECT;Yes;MINY;420.48;HEIGHT;47.52;WIDTH;138.96","arrow SIZE_PARAMS;;MINX;626.4;SCALING_PARAMS;;CLIPPING_ENABLED;No;FIXED_ASPECT;Yes;MINY;185.04;HEIGHT;52.56;WIDTH;57.6","med SIZE_PARAMS;;MINX;649.44;SCALING_PARAMS;;CLIPPING_ENABLED;No;FIXED_ASPECT;Yes;MINY;53.28;HEIGHT;25.2;WIDTH;50.4","max SIZE_PARAMS;;MINX;743.76;SCALING_PARAMS;;CLIPPING_ENABLED;No;FIXED_ASPECT;Yes;MINY;52.56;HEIGHT;25.2;WIDTH;50.4"
    PAGE_ORIENTATION = Landscape
    PAGE_SIZE = Letter
    PAGE_UNITS = Inches
    PAGE_WIDTH_PTS = 792
    PAGE_WIDTH_USER = 11
    -> FeatureWriter [Output]
Creator_9
    COORDS = $(GEOM)
    COORDSYS = LL-WGS84
    GEOMTYPE = 2D Min/Max Box
    NUM = 1
    CREATED -> FeatureReader [INITIATOR]
    CREATED -> Cloner_8
FeatureReader
    ATTRIBUTES = OSM-WMS,"wms_service_name,wms_service_title,wms_service_abstract,wms_layer_name,wms_layer_title,wms_layer_abstract,wms_selected_layers,fme_geometry{0}"
    ATTR_ACCUM_MODE = Only Use Result
    COMBINE_GEOM = Use Result
    DATASET = http://ows.mundialis.de/services/service?
    FEATURETYPES = TOPO-OSM-WMS
    FORMAT = WMS
    INTERACT = Bounding Boxes Intersect
    OUTPUT_FEATURES_DISPLAY = Schema and Data Features
    WMS_MAP_FORMAT = image/png
    WMS_MAP_FORMAT_CHOICES = image/png%image/jpeg
    WMS_PIPE_DELIM = yes
    WMS_READER_META_ATTRIBUTES = fme_dataset fme_basename
    WMS_SPLIT_REQUEST = no
    WMS_SRS = EPSG:4326
    WMS_SRS_CHOICES = EPSG:4326%EPSG:3068%EPSG:4258%EPSG:2180%EPSG:2100%EPSG:25833%EPSG:31467%EPSG:4674%EPSG:31463%EPSG:31468%EPSG:5243%EPSG:900913%EPSG:4647%EPSG:31466%EPSG:2056%EPSG:3857%EPSG:4839%EPSG:21781%EPSG:29192%EPSG:25832%EPSG:29193%EPSG:32648%EPSG:3034%EPSG:3035%EPSG:4686
    WMS_TRANSPARENT = no
    WMS_USE_SEARCH_ENVELOPE = NO
    WMS_WMS_LAYER_LIST = "{OpenStreetMap WMS}|{OSM-WMS}"
    <OTHER> -> AttributeManager_10
AttributeManager_10
    ATTR_TABLE = SET_TO _order = 1
    -> Sorter_4
Cloner_8
    COPIES = 3
    COPYATT = _copynum
    COPY -> TestFilter_6
TestFilter_6
    DEFAULT_VALUE = <UNFILTERED>
    TEST_LIST = "BOOL_OP,OR,COMPOSITE_TEST,""""""1"""""",TEST_CLAUSE,TEST @Value(_copynum) = 0",@Value(_copynum) = 0,"BOOL_OP,OR,COMPOSITE_TEST,""""""1"""""",TEST_CLAUSE,TEST @Value(_copynum) = 1",@Value(_copynum) = 1
    @Value(_copynum) = 1 -> BoundsExtractor
    <UNFILTERED> -> BoundsExtractor_2
BoundsExtractor
    XMAX = _xmax
    XMIN = _xmin
    YMAX = _ymax
    YMIN = _ymin
    ZMAX = _zmax
    ZMIN = _zmin
    -> Cloner_9
Cloner_9
    COPIES = 5
    COPYATT = _copynum2
    COPY -> AttributeManager_6
AttributeManager_6
    ATTR_TABLE:
      SET_TO x = FME_CONDITIONAL:DEFAULT_VALUE'@sub(@Value(_xmin),1.2*@sub(@Value(_xmax),@Value(_xmin)))'BOOL_OP;OR;COMPOSITE_TEST;1 OR 2;TEST @Value(_copynum2) = 0;TEST @Value(_copynum2) = 4'@sub(@Value(_xmin),1.2*@sub(@Value(_xmax),@Value(_xmin)))'BOOL_OP;OR;COMPOSITE_TEST;1;TEST @Value(_copynum2) = 1'@sum(@Value(_xmax),1.2*@sub(@Value(_xmax),@Value(_xmin)))'BOOL_OP;OR;COMPOSITE_TEST;1;TEST @Value(_copynum2) = 2'@sum(@Value(_xmax),1.2*@sub(@Value(_xmax),@Value(_xmin)))'FME_NUM_CONDITIONS4___
      SET_TO y = FME_CONDITIONAL:DEFAULT_VALUE'@sub(@Value(_ymin),1.2*(1.5/@cos(@pi()*@Value(_xmax)/180))*@sub(@Value(_ymax),@Value(_ymin)))'BOOL_OP;OR;COMPOSITE_TEST;1 OR 2;TEST @Value(_copynum2) = 0;TEST @Value(_copynum2) = 4'@sum(@Value(_ymax),1.2*(1.5/@cos(@pi()*@Value(_xmax)/180))*@sub(@Value(_ymax),@Value(_ymin)))'BOOL_OP;OR;COMPOSITE_TEST;1;TEST @Value(_copynum2) = 1'@sum(@Value(_ymax),1.2*(1.5/@cos(@pi()*@Value(_xmax)/180))*@sub(@Value(_ymax),@Value(_ymin)))'BOOL_OP;OR;COMPOSITE_TEST;1;TEST @Value(_copynum2) = 2'@sub(@Value(_ymin),1.2*(1.5/@cos(@pi()*@Value(_xmax)/180))*@sub(@Value(_ymax),@Value(_ymin)))'FME_NUM_CONDITIONS4___
    -> GeometryRemover_2
GeometryRemover_2
    -> VertexCreator_10
VertexCreator_10
    MEASURE_TYPE = Continuous
    MISSING_VAL_MODE = Compute
    MODE_NAME = Add Point
    XVAL = @Value(x)
    YVAL = @Value(y)
    -> LineBuilder_7
LineBuilder_7
    ACCUM_INPUT_ATTRS = Use Attributes From One Feature
    REMOVE_DUPLICATES = NO
    POLYGON -> FeatureReader_2 [INITIATOR]
FeatureReader_2
    ATTRIBUTES = OSM-WMS,"wms_service_name,wms_service_title,wms_service_abstract,wms_layer_name,wms_layer_title,wms_layer_abstract,wms_selected_layers,fme_geometry{0}"
    ATTR_ACCUM_MODE = Only Use Result
    COMBINE_GEOM = Use Result
    DATASET = http://ows.mundialis.de/services/service?
    FEATURETYPES = TOPO-OSM-WMS
    FORMAT = WMS
    INTERACT = Bounding Boxes Intersect
    OUTPUT_FEATURES_DISPLAY = Schema and Data Features
    WMS_MAP_FORMAT = image/png
    WMS_MAP_FORMAT_CHOICES = image/png%image/jpeg
    WMS_PIPE_DELIM = yes
    WMS_READER_META_ATTRIBUTES = fme_dataset fme_basename
    WMS_SPLIT_REQUEST = no
    WMS_SRS = EPSG:4326
    WMS_SRS_CHOICES = EPSG:4326%EPSG:3068%EPSG:4258%EPSG:2180%EPSG:2100%EPSG:25833%EPSG:31467%EPSG:4674%EPSG:31463%EPSG:31468%EPSG:5243%EPSG:900913%EPSG:4647%EPSG:31466%EPSG:2056%EPSG:3857%EPSG:4839%EPSG:21781%EPSG:29192%EPSG:25832%EPSG:29193%EPSG:32648%EPSG:3034%EPSG:3035%EPSG:4686
    WMS_TRANSPARENT = no
    WMS_USE_SEARCH_ENVELOPE = NO
    WMS_WMS_LAYER_LIST = "{OpenStreetMap WMS}|{OSM-WMS}"
    <OTHER> -> AttributeManager_9
AttributeManager_9
    ATTR_TABLE = SET_TO _order = 1
    -> Sorter_3
BoundsExtractor_2
    XMAX = _xmax
    XMIN = _xmin
    YMAX = _ymax
    YMIN = _ymin
    ZMAX = _zmax
    ZMIN = _zmin
    -> Cloner_10
    -> Cloner_11
    -> Cloner_12
Cloner_11
    COPIES = 16
    COPYATT = _copynum2
    COPY -> AttributeManager_7
AttributeManager_7
    ATTR_TABLE:
      SET_TO x = FME_CONDITIONAL:DEFAULT_VALUE''BOOL_OP;OR;COMPOSITE_TEST;1 OR 2 OR 3 OR 4 OR 5 OR 6;TEST @Value(_copynum2) = 0;TEST @Value(_copynum2) = 4;TEST @Value(_copynum2) = 11;TEST @Value(_copynum2) = 12;TEST @Value(_copynum2) = 15;TEST @Value(_copynum2) = 3'@Value(_xmin)'BOOL_OP;OR;COMPOSITE_TEST;1 OR 2 OR 3 OR 4 OR 5 OR 6;TEST @Value(_copynum2) = 1;TEST @Value(_copynum2) = 9;TEST @Value(_copynum2) = 10;TEST @Value(_copynum2) = 13;TEST @Value(_copynum2) = 14;TEST @Value(_copynum2) = 2'@Value(_xmax)'BOOL_OP;OR;COMPOSITE_TEST;1 OR 2;TEST @Value(_copynum2) = 5;TEST @Value(_copynum2) = 6'@Evaluate(@Value(_xmin)+(@Value(_xmax)-@Value(_xmin))/3)'BOOL_OP;OR;COMPOSITE_TEST;1 OR 2;TEST @Value(_copynum2) = 7;TEST @Value(_copynum2) = 8'@Evaluate(@Value(_xmin)+2*(@Value(_xmax)-@Value(_xmin))/3)'FME_NUM_CONDITIONS5___
      SET_TO y = FME_CONDITIONAL:DEFAULT_VALUE''BOOL_OP;OR;COMPOSITE_TEST;1 OR 2 OR 3 OR 4 OR 5 OR 6;TEST @Value(_copynum2) = 0;TEST @Value(_copynum2) = 4;TEST @Value(_copynum2) = 5;TEST @Value(_copynum2) = 8;TEST @Value(_copynum2) = 1;TEST @Value(_copynum2) = 9'@Value(_ymax)'BOOL_OP;OR;COMPOSITE_TEST;1 OR 2 OR 3 OR 4;TEST @Value(_copynum2) = 3;TEST @Value(_copynum2) = 6;TEST @Value(_copynum2) = 7;TEST @Value(_copynum2) = 2'@Value(_ymin)'BOOL_OP;OR;COMPOSITE_TEST;1 OR 2;TEST @Value(_copynum2) = 10;TEST @Value(_copynum2) = 11'@Evaluate(@Value(_ymax)-(@Value(_ymax)-@Value(_ymin))/4)'BOOL_OP;OR;COMPOSITE_TEST;1 OR 2;TEST @Value(_copynum2) = 12;TEST @Value(_copynum2) = 13'@Evaluate(@Value(_ymax)-(@Value(_ymax)-@Value(_ymin))/2)'BOOL_OP;OR;COMPOSITE_TEST;1 OR 2;TEST @Value(_copynum2) = 14;TEST @Value(_copynum2) = 15'@Evaluate(@Value(_ymax)-3*(@Value(_ymax)-@Value(_ymin))/4)'FME_NUM_CONDITIONS6___
      SET_TO _order = 2
    -> GeometryRemover_3
GeometryRemover_3
    -> VertexCreator_12
VertexCreator_12
    MEASURE_TYPE = Continuous
    MISSING_VAL_MODE = Compute
    MODE_NAME = Add Point
    XVAL = @Value(x)
    YVAL = @Value(y)
    -> LineBuilder_8
LineBuilder_8
    ACCUM_INPUT_ATTRS = Use Attributes From One Feature
    REMOVE_DUPLICATES = No
    LINE -> PDFStyler_23
PDFStyler_23
    COLOR = 1,0,0
    FILL_COLOR = 0.666667,0,0
    FILL_OPACITY = 1.00
    FONT = Arial,18,BOLD
    LINE_CAP_STYLE_PARAM = Butt Cap
    LINE_DASH_PHASE = 0
    LINE_JOIN_STYLE_PARAM = Miter Join
    LINE_MITER_LIMIT = 0.0
    LINE_WIDTH = 2.0
    OPACITY = 1.0
    PDFStyled -> Sorter_2
    PDFStyled -> Sorter_3
    PDFStyled -> Sorter_4
Cloner_10
    COPIES = 5
    COPYATT = _copynum2
    COPY -> AttributeManager_5
AttributeManager_5
    ATTR_TABLE:
      SET_TO x = FME_CONDITIONAL:DEFAULT_VALUE'@sub(@Value(_xmin),0.3*@sub(@Value(_xmax),@Value(_xmin)))'BOOL_OP;OR;COMPOSITE_TEST;1 OR 2;TEST @Value(_copynum2) = 0;TEST @Value(_copynum2) = 4'@sub(@Value(_xmin),0.3*@sub(@Value(_xmax),@Value(_xmin)))'BOOL_OP;OR;COMPOSITE_TEST;1;TEST @Value(_copynum2) = 1'@sum(@Value(_xmax),0.3*@sub(@Value(_xmax),@Value(_xmin)))'BOOL_OP;OR;COMPOSITE_TEST;1;TEST @Value(_copynum2) = 2'@sum(@Value(_xmax),0.3*@sub(@Value(_xmax),@Value(_xmin)))'FME_NUM_CONDITIONS4___
      SET_TO y = FME_CONDITIONAL:DEFAULT_VALUE'@sub(@Value(_ymin),0.3*(1.5/@cos(@pi()*@Value(_ymax)/180))*@sub(@Value(_ymax),@Value(_ymin)))'BOOL_OP;OR;COMPOSITE_TEST;1 OR 2;TEST @Value(_copynum2) = 0;TEST @Value(_copynum2) = 4'@sum(@Value(_ymax),0.3*(1.5/@cos(@pi()*@Value(_ymax)/180))*@sub(@Value(_ymax),@Value(_ymin)))'BOOL_OP;OR;COMPOSITE_TEST;1;TEST @Value(_copynum2) = 1'@sum(@Value(_ymax),0.3*(1.5/@cos(@pi()*@Value(_ymax)/180))*@sub(@Value(_ymax),@Value(_ymin)))'BOOL_OP;OR;COMPOSITE_TEST;1;TEST @Value(_copynum2) = 2'@sub(@Value(_ymin),0.3*(1.5/@cos(@pi()*@Value(_ymax)/180))*@sub(@Value(_ymax),@Value(_ymin)))'FME_NUM_CONDITIONS4___
    -> GeometryRemover
GeometryRemover
    -> VertexCreator
VertexCreator
    MEASURE_TYPE = Continuous
    MISSING_VAL_MODE = Compute
    MODE_NAME = Add Point
    XVAL = @Value(x)
    YVAL = @Value(y)
    -> LineBuilder
LineBuilder
    ACCUM_INPUT_ATTRS = Use Attributes From One Feature
    REMOVE_DUPLICATES = NO
    POLYGON -> FeatureReader_3 [INITIATOR]
FeatureReader_3
    ATTRIBUTES = OSM-WMS,"wms_service_name,wms_service_title,wms_service_abstract,wms_layer_name,wms_layer_title,wms_layer_abstract,wms_selected_layers,fme_geometry{0}"
    ATTR_ACCUM_MODE = Only Use Result
    COMBINE_GEOM = Use Result
    DATASET = http://ows.mundialis.de/services/service?
    FEATURETYPES = TOPO-OSM-WMS
    FORMAT = WMS
    INTERACT = Bounding Boxes Intersect
    OUTPUT_FEATURES_DISPLAY = Schema and Data Features
    WMS_MAP_FORMAT = image/png
    WMS_MAP_FORMAT_CHOICES = image/png%image/jpeg
    WMS_PIPE_DELIM = yes
    WMS_READER_META_ATTRIBUTES = fme_dataset fme_basename
    WMS_SPLIT_REQUEST = no
    WMS_SRS = EPSG:4326
    WMS_SRS_CHOICES = EPSG:4326%EPSG:3068%EPSG:4258%EPSG:2180%EPSG:2100%EPSG:25833%EPSG:31467%EPSG:4674%EPSG:31463%EPSG:31468%EPSG:5243%EPSG:900913%EPSG:4647%EPSG:31466%EPSG:2056%EPSG:3857%EPSG:4839%EPSG:21781%EPSG:29192%EPSG:25832%EPSG:29193%EPSG:32648%EPSG:3034%EPSG:3035%EPSG:4686
    WMS_TRANSPARENT = no
    WMS_USE_SEARCH_ENVELOPE = NO
    WMS_WMS_LAYER_LIST = "{OpenStreetMap WMS}|{OSM-WMS}"
    <OTHER> -> AttributeManager_8
AttributeManager_8
    ATTR_TABLE = SET_TO _order = 1
    -> Sorter_2
Cloner_12
    COPIES = 5
    COPYATT = _copynum2
    COPY -> AttributeManager_11
AttributeManager_11
    ATTR_TABLE:
      SET_TO x = FME_CONDITIONAL:DEFAULT_VALUE''BOOL_OP;COMPOSITE;COMPOSITE_TEST;( 1 OR 2 OR 3 )
         AND 4;TEST @Value(_copynum2) = 0;TEST @Value(_copynum2) = 4;TEST @Value(_copynum2) = 3;TEST $(Tile_num) = 0'@Value(_xmin)'BOOL_OP;COMPOSITE;COMPOSITE_TEST;( 1 OR 2 )
         AND 3;TEST @Value(_copynum2) = 1;TEST @Value(_copynum2) = 2;TEST $(Tile_num) = 0'@Value(_xmax)'BOOL_OP;COMPOSITE;COMPOSITE_TEST;( 1 OR 2 OR 3 )
         AND ( 4 OR 5 OR 6 OR 7 );TEST @Value(_copynum2) = 0;TEST @Value(_copynum2) = 4;TEST @Value(_copynum2) = 3;TEST $(Tile_num) = 1;TEST $(Tile_num) = 4;TEST $(Tile_num) = 7;TEST $(Tile_num) = 10'@Value(_xmin)'BOOL_OP;COMPOSITE;COMPOSITE_TEST;( 1 OR 2 )
         AND ( 3 OR 4 OR 5 OR 6 );TEST @Value(_copynum2) = 1;TEST @Value(_copynum2) = 2;TEST $(Tile_num) = 1;TEST $(Tile_num) = 4;TEST $(Tile_num) = 7;TEST $(Tile_num) = 10'@Evaluate(@Value(_xmin)+(@Value(_xmax)-@Value(_xmin))/3)'BOOL_OP;COMPOSITE;COMPOSITE_TEST;( 1 OR 2 OR 3 )
         AND ( 4 OR 5 OR 6 OR 7 );TEST @Value(_copynum2) = 0;TEST @Value(_copynum2) = 4;TEST @Value(_copynum2) = 3;TEST $(Tile_num) = 2;TEST $(Tile_num) = 5;TEST $(Tile_num) = 8;TEST $(Tile_num) = 11'@Evaluate(@Value(_xmin)+(@Value(_xmax)-@Value(_xmin))/3)'BOOL_OP;COMPOSITE;COMPOSITE_TEST;( 1 OR 2 )
         AND ( 3 OR 4 OR 5 OR 6 );TEST @Value(_copynum2) = 1;TEST @Value(_copynum2) = 2;TEST $(Tile_num) = 2;TEST $(Tile_num) = 5;TEST $(Tile_num) = 8;TEST $(Tile_num) = 11'@Evaluate(@Value(_xmin)+2*(@Value(_xmax)-@Value(_xmin))/3)'BOOL_OP;COMPOSITE;COMPOSITE_TEST;( 1 OR 2 OR 3 )
         AND ( 4 OR 5 OR 6 OR 7 );TEST @Value(_copynum2) = 0;TEST @Value(_copynum2) = 4;TEST @Value(_copynum2) = 3;TEST $(Tile_num) = 3;TEST $(Tile_num) = 6;TEST $(Tile_num) = 9;TEST $(Tile_num) = 12'@Evaluate(@Value(_xmin)+2*(@Value(_xmax)-@Value(_xmin))/3)'BOOL_OP;COMPOSITE;COMPOSITE_TEST;( 1 OR 2 )
         AND ( 3 OR 4 OR 5 OR 6 );TEST @Value(_copynum2) = 1;TEST @Value(_copynum2) = 2;TEST $(Tile_num) = 3;TEST $(Tile_num) = 6;TEST $(Tile_num) = 9;TEST $(Tile_num) = 12'@Value(_xmax)'FME_NUM_CONDITIONS9___
      SET_TO y = FME_CONDITIONAL:DEFAULT_VALUE''BOOL_OP;COMPOSITE;COMPOSITE_TEST;( 1 OR 2 OR 3 )
         AND ( 4 OR 5 OR 6 OR 7 );TEST @Value(_copynum2) = 0;TEST @Value(_copynum2) = 4;TEST @Value(_copynum2) = 1;TEST $(Tile_num) = 0;TEST $(Tile_num) = 1;TEST $(Tile_num) = 2;TEST $(Tile_num) = 3'@Value(_ymax)'BOOL_OP;COMPOSITE;COMPOSITE_TEST;( 1 OR 2 )
         AND ( 3 OR 4 OR 5 );TEST @Value(_copynum2) = 2;TEST @Value(_copynum2) = 3;TEST $(Tile_num) = 1;TEST $(Tile_num) = 2;TEST $(Tile_num) = 3'@Evaluate(@Value(_ymax)-(@Value(_ymax)-@Value(_ymin))/4)'BOOL_OP;COMPOSITE;COMPOSITE_TEST;( 1 OR 2 )
         AND ( 3 );TEST @Value(_copynum2) = 2;TEST @Value(_copynum2) = 3;TEST $(Tile_num) = 0'@Value(_ymin)'BOOL_OP;COMPOSITE;COMPOSITE_TEST;( 1 OR 2 OR 3 )
         AND ( 4 OR 5 OR 6 );TEST @Value(_copynum2) = 0;TEST @Value(_copynum2) = 4;TEST @Value(_copynum2) = 1;TEST $(Tile_num) = 4;TEST $(Tile_num) = 5;TEST $(Tile_num) = 6'@Evaluate(@Value(_ymax)-(@Value(_ymax)-@Value(_ymin))/4)'BOOL_OP;COMPOSITE;COMPOSITE_TEST;( 1 OR 2 )
         AND ( 3 OR 4 OR 5 );TEST @Value(_copynum2) = 2;TEST @Value(_copynum2) = 3;TEST $(Tile_num) = 4;TEST $(Tile_num) = 5;TEST $(Tile_num) = 6'@Evaluate(@Value(_ymax)-(@Value(_ymax)-@Value(_ymin))/2)'BOOL_OP;COMPOSITE;COMPOSITE_TEST;( 1 OR 2 OR 3 )
         AND ( 4 OR 5 OR 6 );TEST @Value(_copynum2) = 0;TEST @Value(_copynum2) = 4;TEST @Value(_copynum2) = 1;TEST $(Tile_num) = 7;TEST $(Tile_num) = 8;TEST $(Tile_num) = 9'@Evaluate(@Value(_ymax)-(@Value(_ymax)-@Value(_ymin))/2)'BOOL_OP;COMPOSITE;COMPOSITE_TEST;( 1 OR 2 )
         AND ( 3 OR 4 OR 5 );TEST @Value(_copynum2) = 2;TEST @Value(_copynum2) = 3;TEST $(Tile_num) = 7;TEST $(Tile_num) = 8;TEST $(Tile_num) = 9'@Evaluate(@Value(_ymax)-3*(@Value(_ymax)-@Value(_ymin))/4)'BOOL_OP;COMPOSITE;COMPOSITE_TEST;( 1 OR 2 OR 3 )
         AND ( 4 OR 5 OR 6 );TEST @Value(_copynum2) = 0;TEST @Value(_copynum2) = 4;TEST @Value(_copynum2) = 1;TEST $(Tile_num) = 10;TEST $(Tile_num) = 11;TEST $(Tile_num) = 12'@Evaluate(@Value(_ymax)-3*(@Value(_ymax)-@Value(_ymin))/4)'BOOL_OP;COMPOSITE;COMPOSITE_TEST;( 1 OR 2 )
         AND ( 3 OR 4 OR 5 );TEST @Value(_copynum2) = 2;TEST @Value(_copynum2) = 3;TEST $(Tile_num) = 10;TEST $(Tile_num) = 11;TEST $(Tile_num) = 12'@Value(_ymin)'FME_NUM_CONDITIONS10___
      SET_TO _order = 3
    -> GeometryRemover_4
GeometryRemover_4
    -> VertexCreator_13
VertexCreator_13
    MEASURE_TYPE = Continuous
    MISSING_VAL_MODE = Compute
    MODE_NAME = Add Point
    XVAL = @Value(x)
    YVAL = @Value(y)
    -> LineBuilder_9
LineBuilder_9
    ACCUM_INPUT_ATTRS = Use Attributes From One Feature
    REMOVE_DUPLICATES = NO
    POLYGON -> PDFStyler_24
PDFStyler_24
    COLOR = 1,0.945098,0.133333
    FILL_COLOR = 0.658824,0.666667,0.160784
    FILL_OPACITY = 0.08
    FONT = Arial,18,BOLD
    LINE_CAP_STYLE_PARAM = Butt Cap
    LINE_DASH_PHASE = 0
    LINE_JOIN_STYLE_PARAM = Miter Join
    LINE_MITER_LIMIT = 0.0
    LINE_WIDTH = 2.0
    OPACITY = 1.0
    PDFStyled -> Sorter_2
    PDFStyled -> Sorter_3
    PDFStyled -> Sorter_4
Note: Sort drawing order with _order
Sorter_4
    SORT_PARM = _order NUMERIC ASCENDING
    SORTED -> PDFPageFormatter_2 [Main]
Note: Sort drawing order with _order
Sorter_3
    SORT_PARM = _order NUMERIC ASCENDING
    SORTED -> PDFPageFormatter_2 [Main3]
Note: Sort drawing order with _order
Sorter_2
    SORT_PARM = _order NUMERIC ASCENDING
    SORTED -> PDFPageFormatter_2 [Main2]
pdf_no_layer (reader PDF2D_1)
    -> AttributeManager_2
AttributeManager_2
    ATTR_TABLE = SET_TO pdf_page_number = FME_CONDITIONAL:DEFAULT_VALUE'_FME_NO_OP_'BOOL_OP;OR;COMPOSITE_TEST;1;TEST @Value(pdf_page_number) = 1'2'BOOL_OP;OR;COMPOSITE_TEST;1;TEST @Value(pdf_page_number) = 2'3'FME_NUM_CONDITIONS3___
    -> FeatureWriter [Output]
Date: Creator
    GEOM = <?xml version="1.0" encoding="US_ASCII" standalone="no" ?><geometry><text><point><coord x="0" y="0"/></point><textString>null</textString><textSize>1</textSize><textRotation>0</textRotation></text></geometry>
    GEOMTYPE = Geometry Object
    NUM = 1
    CREATED -> AttributeExposer_3
AttributeExposer_3
    ATTR_LIST = fme_text_string
    -> AttributeManager_4
AttributeManager_4
    ATTR_TABLE:
      SET_TO fme_type = fme_text
      SET_TO fme_text_size = 10
      SET_TO fme_feature_type = Scale_center
      SET_TO fme_geometry = fme_point
      SET_TO fme_rotation = 0
      SET_TO fme_text_string = @DateTimeFormat($(DATE),%Y-%m-%d)
    -> PDFStyler_22
PDFStyler_22
    COLOR = 0,0,0
    FILL_COLOR = 0,0,0
    FILL_OPACITY = 1.00
    FONT = Arial,18,BOLD
    LINE_CAP_STYLE_PARAM = Butt Cap
    LINE_DASH_PHASE = 0
    LINE_JOIN_STYLE_PARAM = Miter Join
    LINE_MITER_LIMIT = 0.0
    LINE_WIDTH = 1.0
    OPACITY = 1.0
    PDFStyled -> PDFPageFormatter_2 [date]
Creator_8
    GEOM = <?xml version="1.0" encoding="US_ASCII" standalone="no" ?><geometry><text><point><coord x="0" y="0"/></point><textString>PDF export</textString><textSize>1</textSize><textRotation>0</textRotation></text></geometry>
    GEOMTYPE = Geometry Object
    NUM = 1
    CREATED -> PDFStyler_21
PDFStyler_21
    COLOR = 0,0,0
    FILL_COLOR = 0,0,0
    FILL_OPACITY = 1.00
    FONT = Arial,18,BOLD
    LINE_CAP_STYLE_PARAM = Butt Cap
    LINE_DASH_PHASE = 0
    LINE_JOIN_STYLE_PARAM = Miter Join
    LINE_MITER_LIMIT = 0.0
    LINE_WIDTH = 1.0
    OPACITY = 1.0
    PDFStyled -> PDFPageFormatter_2 [Title]
Note: Set the page size and add 'Title', 'Main' and 'Signature' frames. / To control the feature type order in the output 'Layer', they must / be ordered by how they should be drawn using the sorter transformer. / NOTE: All feature types that overlap must be considered in the / same frame (drawing object) or the scale and bounds will not match.
PDFPageFormatter_2
    PAGE_HEIGHT_PTS = 612
    PAGE_HEIGHT_USER = 8.5
    PAGE_NUMBER = 4
    PAGE_OBJECTS = "date FIXED_ASPECT;Yes;WIDTH;108;MINY;511.2;CLIPPING_ENABLED;No;HEIGHT;36;MINX;129.6;SIZE_PARAMS;;SCALING_PARAMS;","signature FIXED_ASPECT;Yes;WIDTH;215.09;MINY;11.8754;CLIPPING_ENABLED;No;HEIGHT;32.1;MINX;559.407;SIZE_PARAMS;;SCALING_PARAMS;","header FIXED_ASPECT;Yes;WIDTH;280.24;MINY;564.574;CLIPPING_ENABLED;No;HEIGHT;37.72;MINX;11.8564;SIZE_PARAMS;;SCALING_PARAMS;","Title FIXED_ASPECT;Yes;WIDTH;108;MINY;511.2;CLIPPING_ENABLED;No;HEIGHT;36;MINX;14.4;SIZE_PARAMS;;SCALING_PARAMS;","Main2 FIXED_ASPECT;Yes;WIDTH;252.22;MINY;259.782;CLIPPING_ENABLED;No;HEIGHT;231.5;MINX;94.8517;SIZE_PARAMS;;SCALING_PARAMS;","Main3 FIXED_ASPECT;Yes;WIDTH;229.58;MINY;261.698;CLIPPING_ENABLED;No;HEIGHT;226.35;MINX;396.65;SIZE_PARAMS;;SCALING_PARAMS;","Main FIXED_ASPECT;Yes;WIDTH;238.52;MINY;8.401;CLIPPING_ENABLED;No;HEIGHT;232.01;MINX;247.592;SIZE_PARAMS;;SCALING_PARAMS;"
    PAGE_ORIENTATION = Landscape
    PAGE_SIZE = Letter
    PAGE_UNITS = Inches
    PAGE_WIDTH_PTS = 792
    PAGE_WIDTH_USER = 11
    -> FeatureWriter [Output]
FeatureWriter
    DATASET = $(DEST_PDF)/$(FILE_name)
    DATASET_ATTR = _dataset
    FEATURE_TYPE_LIST_ATTR = _feature_type
    FORMAT = PDF2D
    PDF2D_COMPRESS_STREAMS = Yes
    PDF2D_DEFAULT_LINE_WIDTH = 1.0
    PDF2D_DEFAULT_OPACITY = 0.4
    PDF2D_DEFAULT_POINT_SIZE = 1.0
    PDF2D_DESTINATION_DATASETTYPE_VALIDATION = Yes
    PDF2D_PAGE_SIZE = Letter
    PDF2D_PANEL_VISIBILITY = Layers
    PDF2D_PDF14_COMPATIBLE = No
    PDF2D_RANDOMIZE_FEATURE_TYPE_COLOR = Yes
    PDF2D_RICH_TEXT = No
    PDF2D_SCALE_TEXT_FONT = No
    PDF2D_WRITE_ATTRIBUTES = Yes
    TOTAL_FEATURES_WRITTEN_ATTR = _total_features_written
    SUMMARY -> Logger_2
Logger_2
    LOG_FEATURE = LOG_ONLY
    MAXCOORDS = 20
    MAXFEATS = 20
    MESSAGE = "Feature is: "
    SEVERITY = INFO

Bookmark: BaseMap & Frame
AttributeCreator
    ATTR_TABLE:
      SET_TO _order = 0
      SET_TO fme_feature_type = BackgroundMap
    -> Sorter
AttributeCreator_2
    ATTR_TABLE:
      SET_TO _order = 1
      SET_TO fme_feature_type = BoundingBox
    -> PDFStyler_3
PDFStyler_3
    COLOR = 0,0,0
    FILL_COLOR = 0,0,0
    FILL_OPACITY = 0
    FONT = Helvetica,9
    LINE_CAP_STYLE_PARAM = Butt Cap
    LINE_DASH_PHASE = 0
    LINE_JOIN_STYLE_PARAM = Miter Join
    LINE_MITER_LIMIT = 0.0
    LINE_WIDTH = 3
    OPACITY = 1.0
    PDFStyled -> Sorter

Bookmark: DEM
FeatureReader_7
    ATTR_ACCUM_MODE = Only Use Result
    COMBINE_GEOM = Use Result
    DATASET = $(Layer_feature)_$(ISO)\02_DEM\DEM_2011_$(ISO).tif
    FORMAT = GEOTIFF
    GEOTIFF_APPLY_GCPS = NO
    GEOTIFF_FEATURE_TYPE_NAME = FORMAT_NAME
    GEOTIFF_IGNORE_RASTER_TYPE_KEY = No
    GEOTIFF_PREFER_FILE_CS_UNITS = Yes
    GEOTIFF_READER_META_ATTRIBUTES = fme_dataset fme_basename
    GEOTIFF_READ_OFFSETS_IN_CS_UNITS = No
    GEOTIFF_USE_SEARCH_ENVELOPE = NO
    INTERACT = <No Spatial Filter>
    OUTPUT_FEATURES_DISPLAY = Schema and Data Features
    <OTHER> -> TestFilter_16
TestFilter_16
    DEFAULT_VALUE = resampling
    TEST_LIST:
      "BOOL_OP,AND,COMPOSITE_TEST,""""""1 AND 2"""""",TEST_CLAUSE,TEST $(SQUARE_SIZE_KM) > 75
      TEST $(Tile_num) = 0",no_resampling,"BOOL_OP,OR,COMPOSITE_TEST,""""""1"""""",TEST_CLAUSE,TEST $(SQUARE_SIZE_KM) > 300",no_resampling
    no_resampling -> Clipper_2 [CLIPPEE]
    resampling -> RasterResampler
RasterResampler
    COLUMNS = 500
    INTERPOLATION_TYPE_NAME = Bicubic
    ROWCOL_OR_CELLSIZE = RowsColumns
    ROWS = 500
    RESAMPLED -> Clipper_2 [CLIPPEE]
Clipper_2
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> RasterBandInterpretationCoercer
    INSIDE -> RasterBandMinMaxExtractor_2
RasterBandInterpretationCoercer
    COLOR_TO_NUMERIC = Bounded cast
    FLOAT_TO_INTEGER = Round
    INTERPRETATION = UInt8
    NUMERIC_TO_NUMERIC = Scale by data values
    -> RGBGradationCalculator
RGBGradationCalculator
    ADJUST = None
    DEST_FORMAT = FME
    LIST_NAME = _color
    NUM = 256
    PALETTE_ALPHA = 255
    PALETTE_ATTR = _palette
    PALETTE_FIRST_KEY = 0
    PALETTE_OMIT_TYPE = No
    PALETTE_TYPE = RGB24
    REVERSE = No
    SEED = 1,0,1; 1,1,0; 0,1,0;0,1,1; 0,0,1
    SEED_FORMAT = FME
    UPPER_HEX = No
    -> RasterPaletteAdder_2
RasterPaletteAdder_2
    PALETTE_ATTR = _palette
    -> AttributeManager_14
AttributeManager_14
    ATTR_TABLE:
      SET_TO _order = 2
      SET_TO fme_feature_type = DEM_raster
    -> Sorter
RasterBandMinMaxExtractor_2
    -> AttributeExploder_2
AttributeExploder_2
    ATTR_NAME_LABEL = _attr_name
    ATTR_VALUE_LABEL = _attr_value
    EXPLODING_TYPE = Features
    KEEP_ATTRIBUTES = No
    KEEP_GEOMETRY = No
    -> AttributeManager_21
AttributeManager_21
    ATTR_TABLE:
      SET_TO max_elevation = FME_CONDITIONAL:DEFAULT_VALUE'_FME_NO_OP_'BOOL_OP;OR;COMPOSITE_TEST;1;TEST @Value(_attr_name) = _band{0}.max'@Value(_attr_value)'FME_NUM_CONDITIONS2___
      SET_TO min_elevation = FME_CONDITIONAL:DEFAULT_VALUE'_FME_NO_OP_'BOOL_OP;OR;COMPOSITE_TEST;1;TEST @Value(_attr_name) = _band{0}.min'@Value(_attr_value)'FME_NUM_CONDITIONS2___
      SET_TO join = 0
    -> TestFilter_9
TestFilter_9
    DEFAULT_VALUE = <UNFILTERED>
    TEST_LIST = "BOOL_OP,OR,COMPOSITE_TEST,""""""1"""""",TEST_CLAUSE,TEST @Value(_attr_name) = _band{0}.max",pass,"BOOL_OP,OR,COMPOSITE_TEST,""""""1"""""",TEST_CLAUSE,TEST @Value(_attr_name) = _band{0}.min",pass
    pass -> FeatureJoiner [RIGHT]
Creator_11
    GEOMTYPE = Geometry Object
    NUM = 5
    CREATED -> TestFilter_13
TestFilter_13
    DEFAULT_VALUE = <UNFILTERED>
    TEST_LIST = "BOOL_OP,OR,COMPOSITE_TEST,""""""1"""""",TEST_CLAUSE,CASE_INSENSITIVE_TEST $(LAYER_TYPE_2_MAP) CONTAINS DEM",ok
    ok -> Cloner_14
Cloner_14
    COPIES = 10
    COPYATT = _copynum
    COPY -> AttributeManager_24
AttributeManager_24
    ATTR_TABLE:
      SET_TO x = FME_CONDITIONAL:DEFAULT_VALUE'@Evaluate(5 + 5*@Value(_copynum))'BOOL_OP;OR;COMPOSITE_TEST;1 OR 2 OR 3;TEST @Value(_creation_instance) = 0;TEST @Value(_creation_instance) = 3;TEST @Value(_creation_instance) = 4'@Evaluate(0 + 5*@Value(_copynum))'FME_NUM_CONDITIONS2___
      SET_TO y = FME_CONDITIONAL:DEFAULT_VALUE'0'BOOL_OP;OR;COMPOSITE_TEST;1 OR 2 OR 3;TEST @Value(_creation_instance) = 0;TEST @Value(_creation_instance) = 1;TEST @Value(_creation_instance) = 4'1'FME_NUM_CONDITIONS2___
    -> VertexCreator_15
VertexCreator_15
    MEASURE_TYPE = Continuous
    MISSING_VAL_MODE = Compute
    MODE_NAME = Add Point
    XVAL = @Value(x)
    YVAL = @Value(y)
    -> LineBuilder_11
LineBuilder_11
    ACCUM_INPUT_ATTRS = Use Attributes From One Feature
    GROUP_BY = _copynum
    REMOVE_DUPLICATES = No
    POLYGON -> PDFStyler_39
PDFStyler_39
    COLOR = 0,0,0
    FILL_COLOR = FME_CONDITIONAL:DEFAULT_VALUE''BOOL_OP;OR;COMPOSITE_TEST;1;TEST @Value(_copynum) = 0'1,0,1'BOOL_OP;OR;COMPOSITE_TEST;1;TEST @Value(_copynum) = 1'1,0.815,0.2'BOOL_OP;OR;COMPOSITE_TEST;1;TEST @Value(_copynum) = 2'0.807,1,0'BOOL_OP;OR;COMPOSITE_TEST;1;TEST @Value(_copynum) = 3'0.4,1,0'BOOL_OP;OR;COMPOSITE_TEST;1;TEST @Value(_copynum) = 4'0,1,0'BOOL_OP;OR;COMPOSITE_TEST;1;TEST @Value(_copynum) = 5'0,1,0.4'BOOL_OP;OR;COMPOSITE_TEST;1;TEST @Value(_copynum) = 6'0,1,0.792'BOOL_OP;OR;COMPOSITE_TEST;1;TEST @Value(_copynum) = 7'0,0.8,1'BOOL_OP;OR;COMPOSITE_TEST;1;TEST @Value(_copynum) = 8'0,0.407,1'BOOL_OP;OR;COMPOSITE_TEST;1;TEST @Value(_copynum) = 9'0,0,1'FME_NUM_CONDITIONS11___
    FILL_OPACITY = 1.00
    FONT = Arial
    LINE_CAP_STYLE_PARAM = Butt Cap
    LINE_DASH_PHASE = 0
    LINE_JOIN_STYLE_PARAM = Miter Join
    LINE_MITER_LIMIT = 0.0
    LINE_WIDTH = 1.0
    OPACITY = 1.0
    PDFStyled -> PDFPageFormatter [DEM Scale]
Creator_12
    GEOM = <?xml version="1.0" encoding="US_ASCII" standalone="no" ?><geometry><text><point><coord x="0" y="0"/></point><textString> </textString><textSize>1</textSize><textRotation>0</textRotation></text></geometry>
    GEOMTYPE = Geometry Object
    NUM = 1
    CREATED -> AttributeManager_25
AttributeManager_25
    ATTR_TABLE = SET_TO join = 0
    -> FeatureJoiner [LEFT]
FeatureJoiner
    ATTR_CONFLICT_RES = Use Left
    GEOMETRY_HANDLING = Use Left
    JOIN_KEYS = join join AUTO
    JOIN_MODE = Inner
    JOINED -> AttributeManager_26
AttributeManager_26
    ATTR_TABLE:
      REMOVE _creation_instance
      REMOVE join
      REMOVE _attr_name
      REMOVE _attr_value
      RENAME_SET_VALUE max_elevation > fme_text_string
      RENAME_SET_VALUE min_elevation > fme_text_string
    -> StatisticsCalculator
StatisticsCalculator
    CALCULATION_MODE = NUMERIC
    FEAT_STATS = fme_text_string,NUMERIC_MODE,,,,,MEAN,,,,,,,
    COMPLETE -> TestFilter_10
TestFilter_10
    DEFAULT_VALUE = min
    TEST_LIST = "BOOL_OP,OR,COMPOSITE_TEST,""""""1"""""",TEST_CLAUSE,TEST @Value(fme_text_string) > @Value(fme_text_string.mean)",max
    max -> AttributeManager_28
    max -> AttributeManager_27
    min -> AttributeManager_29
AttributeManager_27
    ATTR_TABLE:
      SET_TO fme_text_string = @Evaluate(@round(@Value(fme_text_string.mean),0))
      REMOVE fme_text_string.mean
      SET_TO fme_text_string = @Value(fme_text_string) [m]
    -> PDFStyler_40
PDFStyler_40
    COLOR = 0,0,0
    FILL_COLOR = 0,0,0
    FILL_OPACITY = 1.00
    FONT = MS Shell Dlg 2,12
    LINE_CAP_STYLE_PARAM = Butt Cap
    LINE_DASH_PHASE = 0
    LINE_JOIN_STYLE_PARAM = Miter Join
    LINE_MITER_LIMIT = 0.0
    LINE_WIDTH = 1.0
    OPACITY = 1.0
    PDFStyled -> PDFPageFormatter [med]
AttributeManager_28
    ATTR_TABLE:
      SET_TO fme_text_string = @Value(fme_text_string) [m]
      REMOVE fme_text_string.mean
    -> PDFStyler_41
PDFStyler_41
    COLOR = 0,0,0
    FILL_COLOR = 0,0,0
    FILL_OPACITY = 1.00
    FONT = MS Shell Dlg 2,12
    LINE_CAP_STYLE_PARAM = Butt Cap
    LINE_DASH_PHASE = 0
    LINE_JOIN_STYLE_PARAM = Miter Join
    LINE_MITER_LIMIT = 0.0
    LINE_WIDTH = 1.0
    OPACITY = 1.0
    PDFStyled -> PDFPageFormatter [max]
AttributeManager_29
    ATTR_TABLE:
      SET_TO fme_text_string = @Value(fme_text_string) [m] AMSL
      REMOVE fme_text_string.mean
    -> PDFStyler_42
PDFStyler_42
    COLOR = 0,0,0
    FILL_COLOR = 0,0,0
    FILL_OPACITY = 1.00
    FONT = MS Shell Dlg 2,12
    LINE_CAP_STYLE_PARAM = Butt Cap
    LINE_DASH_PHASE = 0
    LINE_JOIN_STYLE_PARAM = Miter Join
    LINE_MITER_LIMIT = 0.0
    LINE_WIDTH = 1.0
    OPACITY = 1.0
    PDFStyled -> PDFPageFormatter [min]

Bookmark: Contour
FeatureReader_8
    ATTR_ACCUM_MODE = Only Use Result
    COMBINE_GEOM = Use Result
    DATASET = $(Layer_feature)_$(ISO)\02_DEM\Contour_2011_$(ISO).shp
    FORMAT = SHAPEFILE
    INTERACT = <No Spatial Filter>
    OUTPUT_FEATURES_DISPLAY = Schema and Data Features
    SHAPEFILE_DONUT_DETECTION = ORIENTATION
    SHAPEFILE_ENCODING = fme-source-encoding
    SHAPEFILE_MEASURES_AS_Z = No
    SHAPEFILE_NUMERIC_TYPE_ATTRIBUTE_HANDLING = STANDARD_TYPES
    SHAPEFILE_READ_BLANK_AS = MISSING
    SHAPEFILE_REPORT_BAD_GEOMETRY = No
    SHAPEFILE_TRIM_PRECEDING_SPACES = Yes
    SHAPEFILE_USE_SEARCH_ENVELOPE = NO
    <OTHER> -> Clipper_3 [CLIPPEE]
Clipper_3
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> AttributeExposer_4
AttributeExposer_4
    ATTR_LIST = Elevation
    -> AttributeManager_17
AttributeManager_17
    ATTR_TABLE:
      SET_TO BigLine = @Evaluate(@Value(Elevation)%100)
      SET_TO fme_feature_type = ContourLinesRaster
    -> AttributeCreator_3
AttributeCreator_3
    ATTR_TABLE:
      SET_TO _order = 3
      SET_TO pdf_point_width = 1.5
      SET_TO color = FME_CONDITIONAL:DEFAULT_VALUE'0,0,0'BOOL_OP;OR;COMPOSITE_TEST;1;TEST @Value(BigLine) = 0'0.2,0.2,0.2'FME_NUM_CONDITIONS2___
      SET_TO line_width = FME_CONDITIONAL:DEFAULT_VALUE'1'BOOL_OP;OR;COMPOSITE_TEST;1;TEST @Value(BigLine) = 0'2'FME_NUM_CONDITIONS2___
    -> PDFStyler_38
PDFStyler_38
    COLOR = @Value(color)
    FILL_COLOR = @Value(color)
    FILL_OPACITY = 0.72
    FONT = Helvetica,14,ITALIC
    LINE_CAP_STYLE_PARAM = Butt Cap
    LINE_DASH_PHASE = 0
    LINE_JOIN_STYLE_PARAM = Miter Join
    LINE_MITER_LIMIT = 0.0
    LINE_WIDTH = @Value(line_width)
    OPACITY = 1.0
    PDFStyled -> Sorter

Bookmark: PopDens
FeatureReader_9
    ATTRIBUTES = GEOTIFF,
    ATTR_ACCUM_MODE = Only Use Result
    COMBINE_GEOM = Use Result
    DATASET = $(Layer_feature)_$(ISO)\03_Population_Density/raster_pop_dens_$(ISO)_100m.tif
    FORMAT = GEOTIFF
    GEOTIFF_APPLY_GCPS = NO
    GEOTIFF_FEATURE_TYPE_NAME = FORMAT_NAME
    GEOTIFF_IGNORE_RASTER_TYPE_KEY = No
    GEOTIFF_PREFER_FILE_CS_UNITS = Yes
    GEOTIFF_READER_META_ATTRIBUTES = fme_dataset fme_basename
    GEOTIFF_READ_OFFSETS_IN_CS_UNITS = No
    GEOTIFF_USE_SEARCH_ENVELOPE = NO
    INTERACT = <No Spatial Filter>
    OUTPUT_FEATURES_DISPLAY = Schema and Data Features
    GEOTIFF -> Clipper_5 [CLIPPEE]
Clipper_5
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> RasterBandInterpretationCoercer_2
    INSIDE -> RasterBandMinMaxExtractor_3
RasterBandInterpretationCoercer_2
    COLOR_TO_NUMERIC = Bounded cast
    FLOAT_TO_INTEGER = Round
    INTERPRETATION = UInt8
    NUMERIC_TO_NUMERIC = Scale by data values
    -> RGBGradationCalculator_2
RGBGradationCalculator_2
    ADJUST = None
    DEST_FORMAT = FME
    LIST_NAME = _color
    NUM = 256
    PALETTE_ALPHA = 255
    PALETTE_ATTR = _palette
    PALETTE_FIRST_KEY = 0
    PALETTE_OMIT_TYPE = No
    PALETTE_TYPE = RGB24
    REVERSE = No
    SEED = 1,1,1; 1,0,0; 0.2,0,0
    SEED_FORMAT = FME
    UPPER_HEX = No
    -> RasterPaletteAdder_3
RasterPaletteAdder_3
    PALETTE_ATTR = _palette
    -> AttributeManager_19
AttributeManager_19
    ATTR_TABLE:
      SET_TO _order = 2
      SET_TO fme_feature_type = PopDens_raster
    -> Sorter
RasterBandMinMaxExtractor_3
    -> AttributeExploder_3
AttributeExploder_3
    ATTR_NAME_LABEL = _attr_name
    ATTR_VALUE_LABEL = _attr_value
    EXPLODING_TYPE = Features
    KEEP_ATTRIBUTES = No
    KEEP_GEOMETRY = No
    -> AttributeManager_30
AttributeManager_30
    ATTR_TABLE:
      SET_TO max_dens = FME_CONDITIONAL:DEFAULT_VALUE'_FME_NO_OP_'BOOL_OP;OR;COMPOSITE_TEST;1;TEST @Value(_attr_name) = _band{0}.max'@Value(_attr_value)'FME_NUM_CONDITIONS2___
      SET_TO min_dens = FME_CONDITIONAL:DEFAULT_VALUE'_FME_NO_OP_'BOOL_OP;OR;COMPOSITE_TEST;1;TEST @Value(_attr_name) = _band{0}.min'@Value(_attr_value)'FME_NUM_CONDITIONS2___
      SET_TO join = 0
    -> TestFilter_11
TestFilter_11
    DEFAULT_VALUE = <UNFILTERED>
    TEST_LIST = "BOOL_OP,OR,COMPOSITE_TEST,""""""1"""""",TEST_CLAUSE,TEST @Value(_attr_name) = _band{0}.max",pass,"BOOL_OP,OR,COMPOSITE_TEST,""""""1"""""",TEST_CLAUSE,TEST @Value(_attr_name) = _band{0}.min",pass
    pass -> FeatureJoiner_2 [RIGHT]
Creator_13
    GEOMTYPE = Geometry Object
    NUM = 5
    CREATED -> TestFilter_15
TestFilter_15
    DEFAULT_VALUE = <UNFILTERED>
    TEST_LIST = "BOOL_OP,OR,COMPOSITE_TEST,""""""1"""""",TEST_CLAUSE,CASE_INSENSITIVE_TEST $(LAYER_TYPE_2_MAP) CONTAINS PopDens",ok
    ok -> Cloner_15
Cloner_15
    COPIES = 10
    COPYATT = _copynum
    COPY -> AttributeManager_31
AttributeManager_31
    ATTR_TABLE:
      SET_TO x = FME_CONDITIONAL:DEFAULT_VALUE'@Evaluate(5 + 5*@Value(_copynum))'BOOL_OP;OR;COMPOSITE_TEST;1 OR 2 OR 3;TEST @Value(_creation_instance) = 0;TEST @Value(_creation_instance) = 3;TEST @Value(_creation_instance) = 4'@Evaluate(0 + 5*@Value(_copynum))'FME_NUM_CONDITIONS2___
      SET_TO y = FME_CONDITIONAL:DEFAULT_VALUE'0'BOOL_OP;OR;COMPOSITE_TEST;1 OR 2 OR 3;TEST @Value(_creation_instance) = 0;TEST @Value(_creation_instance) = 1;TEST @Value(_creation_instance) = 4'1'FME_NUM_CONDITIONS2___
    -> VertexCreator_16
VertexCreator_16
    MEASURE_TYPE = Continuous
    MISSING_VAL_MODE = Compute
    MODE_NAME = Add Point
    XVAL = @Value(x)
    YVAL = @Value(y)
    -> LineBuilder_12
LineBuilder_12
    ACCUM_INPUT_ATTRS = Use Attributes From One Feature
    GROUP_BY = _copynum
    REMOVE_DUPLICATES = No
    POLYGON -> PDFStyler_43
PDFStyler_43
    COLOR = 0,0,0
    FILL_COLOR = FME_CONDITIONAL:DEFAULT_VALUE'0,0,0'BOOL_OP;OR;COMPOSITE_TEST;1;TEST @Value(_copynum) = 0'1,1,1'BOOL_OP;OR;COMPOSITE_TEST;1;TEST @Value(_copynum) = 1'1,0.803,0.803'BOOL_OP;OR;COMPOSITE_TEST;1;TEST @Value(_copynum) = 2'1,0.6,0.6'BOOL_OP;OR;COMPOSITE_TEST;1;TEST @Value(_copynum) = 3'1,0.4,0.4'BOOL_OP;OR;COMPOSITE_TEST;1;TEST @Value(_copynum) = 4'1,0.2,0.2'BOOL_OP;OR;COMPOSITE_TEST;1;TEST @Value(_copynum) = 5'1,0,0'BOOL_OP;OR;COMPOSITE_TEST;1;TEST @Value(_copynum) = 6'0.839,0,0'BOOL_OP;OR;COMPOSITE_TEST;1;TEST @Value(_copynum) = 7'0.6823,0,0'BOOL_OP;OR;COMPOSITE_TEST;1;TEST @Value(_copynum) = 8'0.521,0,0'BOOL_OP;OR;COMPOSITE_TEST;1;TEST @Value(_copynum) = 9'0.345,0,0'FME_NUM_CONDITIONS11___
    FILL_OPACITY = 1.00
    FONT = Arial
    LINE_CAP_STYLE_PARAM = Butt Cap
    LINE_DASH_PHASE = 0
    LINE_JOIN_STYLE_PARAM = Miter Join
    LINE_MITER_LIMIT = 0.0
    LINE_WIDTH = 1.0
    OPACITY = 1.0
    <REJECTED> -> PDFPageFormatter [DEM Scale]
Creator_14
    GEOM = <?xml version="1.0" encoding="US_ASCII" standalone="no" ?><geometry><text><point><coord x="0" y="0"/></point><textString> </textString><textSize>1</textSize><textRotation>0</textRotation></text></geometry>
    GEOMTYPE = Geometry Object
    NUM = 1
    CREATED -> AttributeManager_32
AttributeManager_32
    ATTR_TABLE = SET_TO join = 0
    -> FeatureJoiner_2 [LEFT]
FeatureJoiner_2
    ATTR_CONFLICT_RES = Use Left
    GEOMETRY_HANDLING = Use Left
    JOIN_KEYS = join join AUTO
    JOIN_MODE = Inner
    JOINED -> AttributeManager_33
AttributeManager_33
    ATTR_TABLE:
      REMOVE _creation_instance
      REMOVE join
      REMOVE _attr_name
      REMOVE _attr_value
      RENAME_SET_VALUE max_dens > fme_text_string
      RENAME_SET_VALUE min_dens > fme_text_string
    -> StatisticsCalculator_2
StatisticsCalculator_2
    CALCULATION_MODE = NUMERIC
    FEAT_STATS = fme_text_string,NUMERIC_MODE,,,,,MEAN,,,,,,,
    COMPLETE -> TestFilter_12
TestFilter_12
    DEFAULT_VALUE = min
    TEST_LIST = "BOOL_OP,OR,COMPOSITE_TEST,""""""1"""""",TEST_CLAUSE,TEST @Value(fme_text_string) > @Value(fme_text_string.mean)",max
    max -> AttributeManager_35
    max -> AttributeManager_34
    min -> AttributeManager_37
AttributeManager_34
    ATTR_TABLE:
      SET_TO latmax = @GetWord($(GEOM),2)
      SET_TO latmin = @GetWord($(GEOM),0)
      SET_TO fme_text_string = @Evaluate(10*@Value(fme_text_string.mean)*(1/(@cos((@Value(latmax)+@Value(latmin))/2))))
      SET_TO fme_text_string = @Evaluate(@round(@Value(fme_text_string),2))
      REMOVE fme_text_string.mean
    -> PDFStyler_44
PDFStyler_44
    COLOR = 0,0,0
    FILL_COLOR = 0,0,0
    FILL_OPACITY = 1.00
    FONT = MS Shell Dlg 2,12
    LINE_CAP_STYLE_PARAM = Butt Cap
    LINE_DASH_PHASE = 0
    LINE_JOIN_STYLE_PARAM = Miter Join
    LINE_MITER_LIMIT = 0.0
    LINE_WIDTH = 1.0
    OPACITY = 1.0
    PDFStyled -> PDFPageFormatter [med]
AttributeManager_35
    ATTR_TABLE:
      SET_TO latmax = @GetWord($(GEOM),2)
      SET_TO latmin = @GetWord($(GEOM),0)
      SET_TO fme_text_string = @Evaluate(10*@Value(fme_text_string)*(1/(@cos((@Value(latmax)+@Value(latmin))/2))))
      SET_TO fme_text_string = @Evaluate(@round(@Value(fme_text_string),2))
      REMOVE fme_text_string
      REMOVE fme_text_string.mean
    -> PDFStyler_45
PDFStyler_45
    COLOR = 0,0,0
    FILL_COLOR = 0,0,0
    FILL_OPACITY = 1.00
    FONT = MS Shell Dlg 2,12
    LINE_CAP_STYLE_PARAM = Butt Cap
    LINE_DASH_PHASE = 0
    LINE_JOIN_STYLE_PARAM = Miter Join
    LINE_MITER_LIMIT = 0.0
    LINE_WIDTH = 1.0
    OPACITY = 1.0
    PDFStyled -> PDFPageFormatter [max]
AttributeManager_37
    ATTR_TABLE:
      SET_TO latmax = @GetWord($(GEOM),2)
      SET_TO latmin = @GetWord($(GEOM),0)
      SET_TO fme_text_string = @Evaluate(10*@Value(fme_text_string)*(1/(@cos((@Value(latmax)+@Value(latmin))/2))))
      SET_TO fme_text_string = @Evaluate(@round(@Value(fme_text_string),2))
      SET_TO fme_text_string = @Value(fme_text_string) [cap/km2]
      REMOVE fme_text_string.mean
    -> PDFStyler_46
PDFStyler_46
    COLOR = 0,0,0
    FILL_COLOR = 0,0,0
    FILL_OPACITY = 1.00
    FONT = MS Shell Dlg 2,12
    LINE_CAP_STYLE_PARAM = Butt Cap
    LINE_DASH_PHASE = 0
    LINE_JOIN_STYLE_PARAM = Miter Join
    LINE_MITER_LIMIT = 0.0
    LINE_WIDTH = 1.0
    OPACITY = 1.0
    PDFStyled -> PDFPageFormatter [min]

Bookmark: Tabular subtiles
Creator_2
    GEOMTYPE = Geometry Object
    NUM = 1
    CREATED -> AttributeManager_22
AttributeManager_22
    ATTR_TABLE = SET_TO BB_loc = $(Tile_num)
    -> VertexCreator_6
    -> VertexCreator_7
    -> VertexCreator_8
    -> VertexCreator_11
    -> VertexCreator_9
VertexCreator_6
    MEASURE_TYPE = Continuous
    MISSING_VAL_MODE = Compute
    MODE_NAME = Add Point
    XVAL = FME_CONDITIONAL:DEFAULT_VALUE''BOOL_OP;OR;COMPOSITE_TEST;1;TEST @Value(BB_loc) = 0'0'BOOL_OP;OR;COMPOSITE_TEST;1;TEST @Value(BB_loc) = 1'0'BOOL_OP;OR;COMPOSITE_TEST;1;TEST @Value(BB_loc) = 2'1'BOOL_OP;OR;COMPOSITE_TEST;1;TEST @Value(BB_loc) = 3'2'BOOL_OP;OR;COMPOSITE_TEST;1;TEST @Value(BB_loc) = 4'0'BOOL_OP;OR;COMPOSITE_TEST;1;TEST @Value(BB_loc) = 5'1'BOOL_OP;OR;COMPOSITE_TEST;1;TEST @Value(BB_loc) = 6'2'BOOL_OP;OR;COMPOSITE_TEST;1;TEST @Value(BB_loc) = 7'0'BOOL_OP;OR;COMPOSITE_TEST;1;TEST @Value(BB_loc) = 8'1'BOOL_OP;OR;COMPOSITE_TEST;1;TEST @Value(BB_loc) = 9'2'BOOL_OP;OR;COMPOSITE_TEST;1;TEST @Value(BB_loc) = 10'0'BOOL_OP;OR;COMPOSITE_TEST;1;TEST @Value(BB_loc) = 11'1'BOOL_OP;OR;COMPOSITE_TEST;1;TEST @Value(BB_loc) = 12'2'FME_NUM_CONDITIONS14___
    YVAL = FME_CONDITIONAL:DEFAULT_VALUE''BOOL_OP;OR;COMPOSITE_TEST;1;TEST @Value(BB_loc) = 0'4'BOOL_OP;OR;COMPOSITE_TEST;1;TEST @Value(BB_loc) = 1'4'BOOL_OP;OR;COMPOSITE_TEST;1;TEST @Value(BB_loc) = 2'4'BOOL_OP;OR;COMPOSITE_TEST;1;TEST @Value(BB_loc) = 3'4'BOOL_OP;OR;COMPOSITE_TEST;1;TEST @Value(BB_loc) = 4'3'BOOL_OP;OR;COMPOSITE_TEST;1;TEST @Value(BB_loc) = 5'3'BOOL_OP;OR;COMPOSITE_TEST;1;TEST @Value(BB_loc) = 6'3'BOOL_OP;OR;COMPOSITE_TEST;1;TEST @Value(BB_loc) = 7'2'BOOL_OP;OR;COMPOSITE_TEST;1;TEST @Value(BB_loc) = 8'2'BOOL_OP;OR;COMPOSITE_TEST;1;TEST @Value(BB_loc) = 9'2'BOOL_OP;OR;COMPOSITE_TEST;1;TEST @Value(BB_loc) = 10'1'BOOL_OP;OR;COMPOSITE_TEST;1;TEST @Value(BB_loc) = 11'1'BOOL_OP;OR;COMPOSITE_TEST;1;TEST @Value(BB_loc) = 12'1'FME_NUM_CONDITIONS14___
    -> LineBuilder_4
VertexCreator_7
    MEASURE_TYPE = Continuous
    MISSING_VAL_MODE = Compute
    MODE_NAME = Add Point
    XVAL = FME_CONDITIONAL:DEFAULT_VALUE''BOOL_OP;OR;COMPOSITE_TEST;1;TEST @Value(BB_loc) = 0'3'BOOL_OP;OR;COMPOSITE_TEST;1;TEST @Value(BB_loc) = 1'1'BOOL_OP;OR;COMPOSITE_TEST;1;TEST @Value(BB_loc) = 2'2'BOOL_OP;OR;COMPOSITE_TEST;1;TEST @Value(BB_loc) = 3'3'BOOL_OP;OR;COMPOSITE_TEST;1;TEST @Value(BB_loc) = 4'1'BOOL_OP;OR;COMPOSITE_TEST;1;TEST @Value(BB_loc) = 5'2'BOOL_OP;OR;COMPOSITE_TEST;1;TEST @Value(BB_loc) = 6'3'BOOL_OP;OR;COMPOSITE_TEST;1;TEST @Value(BB_loc) = 7'1'BOOL_OP;OR;COMPOSITE_TEST;1;TEST @Value(BB_loc) = 8'2'BOOL_OP;OR;COMPOSITE_TEST;1;TEST @Value(BB_loc) = 9'3'BOOL_OP;OR;COMPOSITE_TEST;1;TEST @Value(BB_loc) = 10'1'BOOL_OP;OR;COMPOSITE_TEST;1;TEST @Value(BB_loc) = 11'2'BOOL_OP;OR;COMPOSITE_TEST;1;TEST @Value(BB_loc) = 12'3'FME_NUM_CONDITIONS14___
    YVAL = FME_CONDITIONAL:DEFAULT_VALUE''BOOL_OP;OR;COMPOSITE_TEST;1;TEST @Value(BB_loc) = 0'4'BOOL_OP;OR;COMPOSITE_TEST;1;TEST @Value(BB_loc) = 1'4'BOOL_OP;OR;COMPOSITE_TEST;1;TEST @Value(BB_loc) = 2'4'BOOL_OP;OR;COMPOSITE_TEST;1;TEST @Value(BB_loc) = 3'4'BOOL_OP;OR;COMPOSITE_TEST;1;TEST @Value(BB_loc) = 4'3'BOOL_OP;OR;COMPOSITE_TEST;1;TEST @Value(BB_loc) = 5'3'BOOL_OP;OR;COMPOSITE_TEST;1;TEST @Value(BB_loc) = 6'3'BOOL_OP;OR;COMPOSITE_TEST;1;TEST @Value(BB_loc) = 7'2'BOOL_OP;OR;COMPOSITE_TEST;1;TEST @Value(BB_loc) = 8'2'BOOL_OP;OR;COMPOSITE_TEST;1;TEST @Value(BB_loc) = 9'2'BOOL_OP;OR;COMPOSITE_TEST;1;TEST @Value(BB_loc) = 10'1'BOOL_OP;OR;COMPOSITE_TEST;1;TEST @Value(BB_loc) = 11'1'BOOL_OP;OR;COMPOSITE_TEST;1;TEST @Value(BB_loc) = 12'1'FME_NUM_CONDITIONS14___
    -> LineBuilder_4
VertexCreator_8
    MEASURE_TYPE = Continuous
    MISSING_VAL_MODE = Compute
    MODE_NAME = Add Point
    XVAL = FME_CONDITIONAL:DEFAULT_VALUE''BOOL_OP;OR;COMPOSITE_TEST;1;TEST @Value(BB_loc) = 0'3'BOOL_OP;OR;COMPOSITE_TEST;1;TEST @Value(BB_loc) = 1'1'BOOL_OP;OR;COMPOSITE_TEST;1;TEST @Value(BB_loc) = 2'2'BOOL_OP;OR;COMPOSITE_TEST;1;TEST @Value(BB_loc) = 3'3'BOOL_OP;OR;COMPOSITE_TEST;1;TEST @Value(BB_loc) = 4'1'BOOL_OP;OR;COMPOSITE_TEST;1;TEST @Value(BB_loc) = 5'2'BOOL_OP;OR;COMPOSITE_TEST;1;TEST @Value(BB_loc) = 6'3'BOOL_OP;OR;COMPOSITE_TEST;1;TEST @Value(BB_loc) = 7'1'BOOL_OP;OR;COMPOSITE_TEST;1;TEST @Value(BB_loc) = 8'2'BOOL_OP;OR;COMPOSITE_TEST;1;TEST @Value(BB_loc) = 9'3'BOOL_OP;OR;COMPOSITE_TEST;1;TEST @Value(BB_loc) = 10'1'BOOL_OP;OR;COMPOSITE_TEST;1;TEST @Value(BB_loc) = 11'2'BOOL_OP;OR;COMPOSITE_TEST;1;TEST @Value(BB_loc) = 12'3'FME_NUM_CONDITIONS14___
    YVAL = FME_CONDITIONAL:DEFAULT_VALUE''BOOL_OP;OR;COMPOSITE_TEST;1;TEST @Value(BB_loc) = 0'0'BOOL_OP;OR;COMPOSITE_TEST;1;TEST @Value(BB_loc) = 1'3'BOOL_OP;OR;COMPOSITE_TEST;1;TEST @Value(BB_loc) = 2'3'BOOL_OP;OR;COMPOSITE_TEST;1;TEST @Value(BB_loc) = 3'3'BOOL_OP;OR;COMPOSITE_TEST;1;TEST @Value(BB_loc) = 4'2'BOOL_OP;OR;COMPOSITE_TEST;1;TEST @Value(BB_loc) = 5'2'BOOL_OP;OR;COMPOSITE_TEST;1;TEST @Value(BB_loc) = 6'2'BOOL_OP;OR;COMPOSITE_TEST;1;TEST @Value(BB_loc) = 7'1'BOOL_OP;OR;COMPOSITE_TEST;1;TEST @Value(BB_loc) = 8'1'BOOL_OP;OR;COMPOSITE_TEST;1;TEST @Value(BB_loc) = 9'1'BOOL_OP;OR;COMPOSITE_TEST;1;TEST @Value(BB_loc) = 10'0'BOOL_OP;OR;COMPOSITE_TEST;1;TEST @Value(BB_loc) = 11'0'BOOL_OP;OR;COMPOSITE_TEST;1;TEST @Value(BB_loc) = 12'0'FME_NUM_CONDITIONS14___
    -> LineBuilder_4
VertexCreator_11
    MEASURE_TYPE = Continuous
    MISSING_VAL_MODE = Compute
    MODE_NAME = Add Point
    XVAL = FME_CONDITIONAL:DEFAULT_VALUE''BOOL_OP;OR;COMPOSITE_TEST;1;TEST @Value(BB_loc) = 0'0'BOOL_OP;OR;COMPOSITE_TEST;1;TEST @Value(BB_loc) = 1'0'BOOL_OP;OR;COMPOSITE_TEST;1;TEST @Value(BB_loc) = 2'1'BOOL_OP;OR;COMPOSITE_TEST;1;TEST @Value(BB_loc) = 3'2'BOOL_OP;OR;COMPOSITE_TEST;1;TEST @Value(BB_loc) = 4'0'BOOL_OP;OR;COMPOSITE_TEST;1;TEST @Value(BB_loc) = 5'1'BOOL_OP;OR;COMPOSITE_TEST;1;TEST @Value(BB_loc) = 6'2'BOOL_OP;OR;COMPOSITE_TEST;1;TEST @Value(BB_loc) = 7'0'BOOL_OP;OR;COMPOSITE_TEST;1;TEST @Value(BB_loc) = 8'1'BOOL_OP;OR;COMPOSITE_TEST;1;TEST @Value(BB_loc) = 9'2'BOOL_OP;OR;COMPOSITE_TEST;1;TEST @Value(BB_loc) = 10'0'BOOL_OP;OR;COMPOSITE_TEST;1;TEST @Value(BB_loc) = 11'1'BOOL_OP;OR;COMPOSITE_TEST;1;TEST @Value(BB_loc) = 12'2'FME_NUM_CONDITIONS14___
    YVAL = FME_CONDITIONAL:DEFAULT_VALUE''BOOL_OP;OR;COMPOSITE_TEST;1;TEST @Value(BB_loc) = 0'0'BOOL_OP;OR;COMPOSITE_TEST;1;TEST @Value(BB_loc) = 1'3'BOOL_OP;OR;COMPOSITE_TEST;1;TEST @Value(BB_loc) = 2'3'BOOL_OP;OR;COMPOSITE_TEST;1;TEST @Value(BB_loc) = 3'3'BOOL_OP;OR;COMPOSITE_TEST;1;TEST @Value(BB_loc) = 4'2'BOOL_OP;OR;COMPOSITE_TEST;1;TEST @Value(BB_loc) = 5'2'BOOL_OP;OR;COMPOSITE_TEST;1;TEST @Value(BB_loc) = 6'2'BOOL_OP;OR;COMPOSITE_TEST;1;TEST @Value(BB_loc) = 7'1'BOOL_OP;OR;COMPOSITE_TEST;1;TEST @Value(BB_loc) = 8'1'BOOL_OP;OR;COMPOSITE_TEST;1;TEST @Value(BB_loc) = 9'1'BOOL_OP;OR;COMPOSITE_TEST;1;TEST @Value(BB_loc) = 10'0'BOOL_OP;OR;COMPOSITE_TEST;1;TEST @Value(BB_loc) = 11'0'BOOL_OP;OR;COMPOSITE_TEST;1;TEST @Value(BB_loc) = 12'0'FME_NUM_CONDITIONS14___
    -> LineBuilder_4
VertexCreator_9
    MEASURE_TYPE = Continuous
    MISSING_VAL_MODE = Compute
    MODE_NAME = Add Point
    XVAL = FME_CONDITIONAL:DEFAULT_VALUE''BOOL_OP;OR;COMPOSITE_TEST;1;TEST @Value(BB_loc) = 0'0'BOOL_OP;OR;COMPOSITE_TEST;1;TEST @Value(BB_loc) = 1'0'BOOL_OP;OR;COMPOSITE_TEST;1;TEST @Value(BB_loc) = 2'1'BOOL_OP;OR;COMPOSITE_TEST;1;TEST @Value(BB_loc) = 3'2'BOOL_OP;OR;COMPOSITE_TEST;1;TEST @Value(BB_loc) = 4'0'BOOL_OP;OR;COMPOSITE_TEST;1;TEST @Value(BB_loc) = 5'1'BOOL_OP;OR;COMPOSITE_TEST;1;TEST @Value(BB_loc) = 6'2'BOOL_OP;OR;COMPOSITE_TEST;1;TEST @Value(BB_loc) = 7'0'BOOL_OP;OR;COMPOSITE_TEST;1;TEST @Value(BB_loc) = 8'1'BOOL_OP;OR;COMPOSITE_TEST;1;TEST @Value(BB_loc) = 9'2'BOOL_OP;OR;COMPOSITE_TEST;1;TEST @Value(BB_loc) = 10'0'BOOL_OP;OR;COMPOSITE_TEST;1;TEST @Value(BB_loc) = 11'1'BOOL_OP;OR;COMPOSITE_TEST;1;TEST @Value(BB_loc) = 12'2'FME_NUM_CONDITIONS14___
    YVAL = FME_CONDITIONAL:DEFAULT_VALUE''BOOL_OP;OR;COMPOSITE_TEST;1;TEST @Value(BB_loc) = 0'4'BOOL_OP;OR;COMPOSITE_TEST;1;TEST @Value(BB_loc) = 1'4'BOOL_OP;OR;COMPOSITE_TEST;1;TEST @Value(BB_loc) = 2'4'BOOL_OP;OR;COMPOSITE_TEST;1;TEST @Value(BB_loc) = 3'4'BOOL_OP;OR;COMPOSITE_TEST;1;TEST @Value(BB_loc) = 4'3'BOOL_OP;OR;COMPOSITE_TEST;1;TEST @Value(BB_loc) = 5'3'BOOL_OP;OR;COMPOSITE_TEST;1;TEST @Value(BB_loc) = 6'3'BOOL_OP;OR;COMPOSITE_TEST;1;TEST @Value(BB_loc) = 7'2'BOOL_OP;OR;COMPOSITE_TEST;1;TEST @Value(BB_loc) = 8'2'BOOL_OP;OR;COMPOSITE_TEST;1;TEST @Value(BB_loc) = 9'2'BOOL_OP;OR;COMPOSITE_TEST;1;TEST @Value(BB_loc) = 10'1'BOOL_OP;OR;COMPOSITE_TEST;1;TEST @Value(BB_loc) = 11'1'BOOL_OP;OR;COMPOSITE_TEST;1;TEST @Value(BB_loc) = 12'1'FME_NUM_CONDITIONS14___
    -> LineBuilder_4
LineBuilder_4
    ACCUM_INPUT_ATTRS = Use Attributes From One Feature
    GROUP_BY = BB_loc
    REMOVE_DUPLICATES = No
    POLYGON -> PDFStyler_15
North_2: Creator
    GEOM = <?xml version="1.0" encoding="US_ASCII" standalone="no" ?><geometry><text><point><coord x="0" y="0"/></point><textString>null</textString><textSize>10</textSize><textRotation>0</textRotation></text></geometry>
    GEOMTYPE = Geometry Object
    NUM = 1
    CREATED -> AttributeManager_23
AttributeManager_23
    ATTR_TABLE:
      SET_TO BB_loc = $(Tile_num)
      SET_TO fme_text_string = FME_CONDITIONAL:DEFAULT_VALUE'_FME_NO_OP_'BOOL_OP;OR;COMPOSITE_TEST;1;TEST @Value(BB_loc) = 0'Full BoundingBox'BOOL_OP;OR;COMPOSITE_TEST;1;TEST @Value(BB_loc) = 1'Sub-tile n° (0,3)'BOOL_OP;OR;COMPOSITE_TEST;1;TEST @Value(BB_loc) = 2'Sub-tile n° (1,3)'BOOL_OP;OR;COMPOSITE_TEST;1;TEST @Value(BB_loc) = 3'Sub-tile n° (2,3)'BOOL_OP;OR;COMPOSITE_TEST;1;TEST @Value(BB_loc) = 4'Sub-tile n° (0,2)'BOOL_OP;OR;COMPOSITE_TEST;1;TEST @Value(BB_loc) = 5'Sub-tile n° (1,2)'BOOL_OP;OR;COMPOSITE_TEST;1;TEST @Value(BB_loc) = 6'Sub-tile n° (2,2)'BOOL_OP;OR;COMPOSITE_TEST;1;TEST @Value(BB_loc) = 7'Sub-tile n° (0,1)'BOOL_OP;OR;COMPOSITE_TEST;1;TEST @Value(BB_loc) = 8'Sub-tile n° (1,1)'BOOL_OP;OR;COMPOSITE_TEST;1;TEST @Value(BB_loc) = 9'Sub-tile n° (2,1)'BOOL_OP;OR;COMPOSITE_TEST;1;TEST @Value(BB_loc) = 10'Sub-tile n° (0,0)'BOOL_OP;OR;COMPOSITE_TEST;1;TEST @Value(BB_loc) = 11'Sub-tile n° (1,0)'BOOL_OP;OR;COMPOSITE_TEST;1;TEST @Value(BB_loc) = 12'Sub-tile n° (2,0)'FME_NUM_CONDITIONS14___
    -> PDFStyler_16
PDFStyler_16
    COLOR = 0,0.333333,1
    FILL_COLOR = 0,0.333333,1
    FILL_OPACITY = 1.00
    FONT = MS Shell Dlg 2,12,BOLD
    LINE_CAP_STYLE_PARAM = Butt Cap
    LINE_DASH_PHASE = 0
    LINE_JOIN_STYLE_PARAM = Miter Join
    LINE_MITER_LIMIT = 0.0
    LINE_WIDTH = 1.5
    OPACITY = 1.0
    PDFStyled -> PDFPageFormatter [coord]
Creator
    GEOM = <?xml version="1.0" encoding="US_ASCII" standalone="no" ?><geometry><line><coord x="0" y="4"/><coord x="3" y="4"/><coord x="3" y="0"/><coord x="0" y="0"/><coord x="0" y="4"/><coord x="1" y="4"/><coord x="1" y="0"/><coord x="2" y="0"/><coord x="2" y="4"/><coord x="3" y="4"/><coord x="3" y="3"/><coord x="0" y="3"/><coord x="0" y="2"/><coord x="3" y="2"/><coord x="3" y="1"/><coord x="0" y="1"/></line></geometry>
    GEOMTYPE = Geometry Object
    NUM = 1
    CREATED -> PDFStyler_15
PDFStyler_15
    COLOR = 0,0,0
    FILL_COLOR = 0,0.333333,1
    FILL_OPACITY = 0.51
    FONT = MS Shell Dlg 2,12,BOLD
    LINE_CAP_STYLE_PARAM = Butt Cap
    LINE_DASH_PHASE = 0
    LINE_JOIN_STYLE_PARAM = Miter Join
    LINE_MITER_LIMIT = 0.0
    LINE_WIDTH = 1.5
    OPACITY = 1.0
    PDFStyled -> PDFPageFormatter [tabular]

Bookmark: Scale
Scale_left: Creator
    GEOM = <?xml version="1.0" encoding="US_ASCII" standalone="no" ?><geometry><text><point><coord x="0" y="0"/></point><textString>null</textString><textSize>1</textSize><textRotation>0</textRotation></text></geometry>
    GEOMTYPE = Geometry Object
    NUM = 1
    CREATED -> AttributeExposer_2
AttributeExposer_2
    ATTR_LIST = fme_text_string
    -> AttributeManager_20
AttributeManager_20
    ATTR_TABLE:
      SET_TO fme_type = fme_text
      SET_TO fme_text_size = 10
      SET_TO fme_feature_type = Scale_center
      SET_TO fme_geometry = fme_point
      SET_TO fme_rotation = 0
      SET_TO fme_text_string = FME_CONDITIONAL:DEFAULT_VALUE'@Evaluate(@round($(SQUARE_SIZE_KM)/12,1))'BOOL_OP;OR;COMPOSITE_TEST;1;TEST $(Tile_num) = 0'@Evaluate(@round($(SQUARE_SIZE_KM)/4,1))'FME_NUM_CONDITIONS2___
    -> PDFStyler_11
PDFStyler_11
    COLOR = 0,0,0
    FILL_COLOR = 0,0,0
    FILL_OPACITY = 1.00
    FONT = Helvetica,12
    LINE_CAP_STYLE_PARAM = Butt Cap
    LINE_DASH_PHASE = 0
    LINE_JOIN_STYLE_PARAM = Miter Join
    LINE_MITER_LIMIT = 0.0
    LINE_WIDTH = 1.0
    OPACITY = 1.0
    PDFStyled -> PDFPageFormatter [Scale 1]
Scale_center: Creator
    GEOM = <?xml version="1.0" encoding="US_ASCII" standalone="no" ?><geometry><text><point><coord x="0" y="0"/></point><textString>null</textString><textSize>1</textSize><textRotation>0</textRotation></text></geometry>
    GEOMTYPE = Geometry Object
    NUM = 1
    CREATED -> AttributeExposer
AttributeExposer
    ATTR_LIST = fme_text_string
    -> AttributeManager_18
AttributeManager_18
    ATTR_TABLE:
      SET_TO fme_text_string = FME_CONDITIONAL:DEFAULT_VALUE'@Evaluate(@round($(SQUARE_SIZE_KM)/24,1))'BOOL_OP;OR;COMPOSITE_TEST;1;TEST $(Tile_num) = 0'@Evaluate(@round($(SQUARE_SIZE_KM)/8,1))'FME_NUM_CONDITIONS2___
      SET_TO fme_type = fme_text
      SET_TO fme_text_size = 10
      SET_TO fme_feature_type = Scale_center
      SET_TO fme_geometry = fme_point
      SET_TO fme_rotation = 0
    -> PDFStyler_12
PDFStyler_12
    COLOR = 0,0,0
    FILL_COLOR = 0,0,0
    FILL_OPACITY = 1.00
    FONT = Helvetica,12
    LINE_CAP_STYLE_PARAM = Butt Cap
    LINE_DASH_PHASE = 0
    LINE_JOIN_STYLE_PARAM = Miter Join
    LINE_MITER_LIMIT = 0.0
    LINE_WIDTH = 1.0
    OPACITY = 1.0
    PDFStyled -> PDFPageFormatter [Scale 2]
Creator_4
    GEOMTYPE = Geometry Object
    NUM = 1
    CREATED -> Cloner_6
Cloner_6
    COPIES = 5
    COPYATT = _copynum
    COPY -> VertexCreator_3
VertexCreator_3
    MEASURE_TYPE = Continuous
    MISSING_VAL_MODE = Compute
    MODE_NAME = Add Point
    XVAL = FME_CONDITIONAL:DEFAULT_VALUE''BOOL_OP;OR;COMPOSITE_TEST;1 OR 2;TEST @Value(_copynum) = 0;TEST @Value(_copynum) = 4'0'BOOL_OP;OR;COMPOSITE_TEST;1;TEST @Value(_copynum) = 1'0'BOOL_OP;OR;COMPOSITE_TEST;1;TEST @Value(_copynum) = 2'8'BOOL_OP;OR;COMPOSITE_TEST;1;TEST @Value(_copynum) = 3'8'FME_NUM_CONDITIONS5___
    YVAL = FME_CONDITIONAL:DEFAULT_VALUE''BOOL_OP;OR;COMPOSITE_TEST;1 OR 2;TEST @Value(_copynum) = 0;TEST @Value(_copynum) = 4'0'BOOL_OP;OR;COMPOSITE_TEST;1;TEST @Value(_copynum) = 1'1'BOOL_OP;OR;COMPOSITE_TEST;1;TEST @Value(_copynum) = 2'1'BOOL_OP;OR;COMPOSITE_TEST;1;TEST @Value(_copynum) = 3'0'FME_NUM_CONDITIONS5___
    -> LineBuilder_6
LineBuilder_6
    ACCUM_INPUT_ATTRS = Use Attributes From One Feature
    REMOVE_DUPLICATES = No
    POLYGON -> Cloner
Cloner
    COPIES = 2
    COPYATT = _copynum
    COPY -> TestFilter_2
TestFilter_2
    DEFAULT_VALUE = right
    TEST_LIST = "BOOL_OP,OR,COMPOSITE_TEST,""""""1"""""",TEST_CLAUSE,TEST @Value(_copynum) = 0",left
    left -> PDFStyler_9
    right -> PDFStyler_10
PDFStyler_9
    COLOR = 0,0,0
    FILL_COLOR = 1,1,1
    FILL_OPACITY = 1.00
    FONT = MS Shell Dlg 2,12,BOLD
    LINE_CAP_STYLE_PARAM = Butt Cap
    LINE_DASH_PHASE = 0
    LINE_JOIN_STYLE_PARAM = Miter Join
    LINE_MITER_LIMIT = 0.0
    LINE_WIDTH = 2
    OPACITY = 1.0
    PDFStyled -> PDFPageFormatter [left_scale]
PDFStyler_10
    COLOR = 0,0,0
    FILL_COLOR = 0,0,0
    FILL_OPACITY = 1.00
    FONT = MS Shell Dlg 2,12,BOLD
    LINE_CAP_STYLE_PARAM = Butt Cap
    LINE_DASH_PHASE = 0
    LINE_JOIN_STYLE_PARAM = Miter Join
    LINE_MITER_LIMIT = 0.0
    LINE_WIDTH = 2
    OPACITY = 1.0
    PDFStyled -> PDFPageFormatter [right_scale]
Units: Creator
    GEOM = <?xml version="1.0" encoding="US_ASCII" standalone="no" ?><geometry><text><point><coord x="0" y="0"/></point><textString>Kilometers</textString><textSize>10</textSize><textRotation>0</textRotation></text></geometry>
    GEOMTYPE = Geometry Object
    NUM = 1
    CREATED -> PDFStyler_7
PDFStyler_7
    COLOR = 0,0,0
    FILL_COLOR = 0,0,0
    FILL_OPACITY = 1.00
    FONT = Helvetica,12
    LINE_CAP_STYLE_PARAM = Butt Cap
    LINE_DASH_PHASE = 0
    LINE_JOIN_STYLE_PARAM = Miter Join
    LINE_MITER_LIMIT = 0.0
    LINE_WIDTH = 1.0
    OPACITY = 1.0
    PDFStyled -> PDFPageFormatter [Units]
Scale_0_km_: Creator
    GEOM = <?xml version="1.0" encoding="US_ASCII" standalone="no" ?><geometry><text><point><coord x="0" y="0"/></point><textString>null</textString><textSize>10</textSize><textRotation>0</textRotation></text></geometry>
    GEOMTYPE = Geometry Object
    NUM = 1
    CREATED -> AttributeManager_15
AttributeManager_15
    ATTR_TABLE = SET_TO fme_text_string = 0
    -> PDFStyler_13
PDFStyler_13
    COLOR = 0,0,0
    FILL_COLOR = 0,0,0
    FILL_OPACITY = 1.00
    FONT = Helvetica,12
    LINE_CAP_STYLE_PARAM = Butt Cap
    LINE_DASH_PHASE = 0
    LINE_JOIN_STYLE_PARAM = Miter Join
    LINE_MITER_LIMIT = 0.0
    LINE_WIDTH = 1.0
    OPACITY = 1.0
    PDFStyled -> PDFPageFormatter [Scale 3]

Bookmark: Printed features preview
Creator_7
    GEOMTYPE = Geometry Object
    NUM = 5
    CREATED -> Cloner_3
Cloner_3
    COPIES = 7
    COPYATT = _offset
    COPY -> Cloner_7
Cloner_7
    COPIES = 4
    COPYATT = _offset_y
    COPY -> VertexCreator_4
VertexCreator_4
    MEASURE_TYPE = Continuous
    MISSING_VAL_MODE = Compute
    MODE_NAME = Add Point
    XVAL = FME_CONDITIONAL:DEFAULT_VALUE''BOOL_OP;OR;COMPOSITE_TEST;1 OR 2;TEST @Value(_creation_instance) = 0;TEST @Value(_creation_instance) = 4'0 + 4*@Value(_offset)'BOOL_OP;OR;COMPOSITE_TEST;1;TEST @Value(_creation_instance) = 1'1 + 4*@Value(_offset)'BOOL_OP;OR;COMPOSITE_TEST;1;TEST @Value(_creation_instance) = 2'1 + 4*@Value(_offset)'BOOL_OP;OR;COMPOSITE_TEST;1;TEST @Value(_creation_instance) = 3'0 + 4*@Value(_offset)'FME_NUM_CONDITIONS5___
    YVAL = FME_CONDITIONAL:DEFAULT_VALUE''BOOL_OP;OR;COMPOSITE_TEST;1 OR 2;TEST @Value(_creation_instance) = 0;TEST @Value(_creation_instance) = 4'1 + 2*@Value(_offset_y)'BOOL_OP;OR;COMPOSITE_TEST;1;TEST @Value(_creation_instance) = 1'1 + 2*@Value(_offset_y)'BOOL_OP;OR;COMPOSITE_TEST;1;TEST @Value(_creation_instance) = 2'0  + 2*@Value(_offset_y)'BOOL_OP;OR;COMPOSITE_TEST;1;TEST @Value(_creation_instance) = 3'0  + 2*@Value(_offset_y)'FME_NUM_CONDITIONS5___
    -> TestFilter_5
TestFilter_5
    DEFAULT_VALUE = pass
    TEST_LIST:
      "BOOL_OP,AND,COMPOSITE_TEST,""""""1 AND 2 AND 3 AND 4"""""",TEST_CLAUSE,TEST @GetWord($(LAYER_TYPE_2_MAP),0) != OSM
      TEST @GetWord($(LAYER_TYPE_2_MAP),1) != OSM
      TEST @GetWord($(LAYER_TYPE_2_MAP),2) != OSM
      TEST @GetWord($(LAYER_TYPE_2_MAP),4) != OSM",pass,"BOOL_OP,COMPOSITE,COMPOSITE_TEST,""""""1 AND ( 2 OR 3 ) AND ( 4 )"""""",TEST_CLAUSE,TEST @Value(_creation_instance) = 0
      TEST @Value(_offset) = 6
      TEST @Value(_offset) = 5
      TEST @Value(_offset_y) = 0",delete,"BOOL_OP,AND,COMPOSITE_TEST,""""""1 AND 2 AND 3 AND 4"""""",TEST_CLAUSE,CASE_INSENSITIVE_TEST $(Features_to_print) CONTAINS aerialway
      CASE_INSENSITIVE_TEST @Value(_creation_instance) = 4
      CASE_INSENSITIVE_TEST @Value(_offset) = 0
      CASE_INSENSITIVE_TEST @Value(_offset_y) = 3",delete,"BOOL_OP,AND,COMPOSITE_TEST,""""""1 AND 2 AND 3 AND 4"""""",TEST_CLAUSE,CASE_INSENSITIVE_TEST $(Features_to_print) CONTAINS aeroway
      CASE_INSENSITIVE_TEST @Value(_creation_instance) = 4
      CASE_INSENSITIVE_TEST @Value(_offset) = 1
      CASE_INSENSITIVE_TEST @Value(_offset_y) = 3",delete,"BOOL_OP,AND,COMPOSITE_TEST,""""""1 AND 2 AND 3 AND 4"""""",TEST_CLAUSE,CASE_INSENSITIVE_TEST $(Features_to_print) CONTAINS amenity
      CASE_INSENSITIVE_TEST @Value(_creation_instance) = 4
      CASE_INSENSITIVE_TEST @Value(_offset) = 2
      CASE_INSENSITIVE_TEST @Value(_offset_y) = 3",delete,"BOOL_OP,AND,COMPOSITE_TEST,""""""1 AND 2 AND 3 AND 4"""""",TEST_CLAUSE,CASE_INSENSITIVE_TEST $(Features_to_print) CONTAINS barrier
      CASE_INSENSITIVE_TEST @Value(_creation_instance) = 4
      CASE_INSENSITIVE_TEST @Value(_offset) = 3
      CASE_INSENSITIVE_TEST @Value(_offset_y) = 3",delete,"BOOL_OP,AND,COMPOSITE_TEST,""""""1 AND 2 AND 3 AND 4"""""",TEST_CLAUSE,CASE_INSENSITIVE_TEST $(Features_to_print) CONTAINS boundary
      CASE_INSENSITIVE_TEST @Value(_creation_instance) = 4
      CASE_INSENSITIVE_TEST @Value(_offset) = 4
      CASE_INSENSITIVE_TEST @Value(_offset_y) = 3",delete,"BOOL_OP,AND,COMPOSITE_TEST,""""""1 AND 2 AND 3 AND 4"""""",TEST_CLAUSE,CASE_INSENSITIVE_TEST $(Features_to_print) CONTAINS building
      CASE_INSENSITIVE_TEST @Value(_creation_instance) = 4
      CASE_INSENSITIVE_TEST @Value(_offset) = 5
      CASE_INSENSITIVE_TEST @Value(_offset_y) = 3",delete,"BOOL_OP,AND,COMPOSITE_TEST,""""""1 AND 2 AND 3 AND 4"""""",TEST_CLAUSE,CASE_INSENSITIVE_TEST $(Features_to_print) CONTAINS craft
      CASE_INSENSITIVE_TEST @Value(_creation_instance) = 4
      CASE_INSENSITIVE_TEST @Value(_offset) = 6
      CASE_INSENSITIVE_TEST @Value(_offset_y) = 3",delete,"BOOL_OP,AND,COMPOSITE_TEST,""""""1 AND 2 AND 3 AND 4"""""",TEST_CLAUSE,CASE_INSENSITIVE_TEST $(Features_to_print) CONTAINS emergency
      CASE_INSENSITIVE_TEST @Value(_creation_instance) = 4
      CASE_INSENSITIVE_TEST @Value(_offset) = 0
      CASE_INSENSITIVE_TEST @Value(_offset_y) = 2",delete,"BOOL_OP,AND,COMPOSITE_TEST,""""""1 AND 2 AND 3 AND 4"""""",TEST_CLAUSE,CASE_INSENSITIVE_TEST $(Features_to_print) CONTAINS geological
      CASE_INSENSITIVE_TEST @Value(_creation_instance) = 4
      CASE_INSENSITIVE_TEST @Value(_offset) = 1
      CASE_INSENSITIVE_TEST @Value(_offset_y) = 2",delete,"BOOL_OP,AND,COMPOSITE_TEST,""""""1 AND 2 AND 3 AND 4"""""",TEST_CLAUSE,CASE_INSENSITIVE_TEST $(Features_to_print) CONTAINS highway
      CASE_INSENSITIVE_TEST @Value(_creation_instance) = 4
      CASE_INSENSITIVE_TEST @Value(_offset) = 2
      CASE_INSENSITIVE_TEST @Value(_offset_y) = 2",delete,"BOOL_OP,AND,COMPOSITE_TEST,""""""1 AND 2 AND 3 AND 4"""""",TEST_CLAUSE,CASE_INSENSITIVE_TEST $(Features_to_print) CONTAINS historic
      CASE_INSENSITIVE_TEST @Value(_creation_instance) = 4
      CASE_INSENSITIVE_TEST @Value(_offset) = 3
      CASE_INSENSITIVE_TEST @Value(_offset_y) = 2",delete,"BOOL_OP,AND,COMPOSITE_TEST,""""""1 AND 2 AND 3 AND 4"""""",TEST_CLAUSE,CASE_INSENSITIVE_TEST $(Features_to_print) CONTAINS landuse
      CASE_INSENSITIVE_TEST @Value(_creation_instance) = 4
      CASE_INSENSITIVE_TEST @Value(_offset) = 4
      CASE_INSENSITIVE_TEST @Value(_offset_y) = 2",delete,"BOOL_OP,AND,COMPOSITE_TEST,""""""1 AND 2 AND 3 AND 4"""""",TEST_CLAUSE,CASE_INSENSITIVE_TEST $(Features_to_print) CONTAINS leisure
      CASE_INSENSITIVE_TEST @Value(_creation_instance) = 4
      CASE_INSENSITIVE_TEST @Value(_offset) = 5
      CASE_INSENSITIVE_TEST @Value(_offset_y) = 2",delete,"BOOL_OP,AND,COMPOSITE_TEST,""""""1 AND 2 AND 3 AND 4"""""",TEST_CLAUSE,CASE_INSENSITIVE_TEST $(Features_to_print) CONTAINS man_made
      CASE_INSENSITIVE_TEST @Value(_creation_instance) = 4
      CASE_INSENSITIVE_TEST @Value(_offset) = 6
      CASE_INSENSITIVE_TEST @Value(_offset_y) = 2",delete,"BOOL_OP,AND,COMPOSITE_TEST,""""""1 AND 2 AND 3 AND 4"""""",TEST_CLAUSE,CASE_INSENSITIVE_TEST $(Features_to_print) CONTAINS military
      CASE_INSENSITIVE_TEST @Value(_creation_instance) = 4
      CASE_INSENSITIVE_TEST @Value(_offset) = 0
      CASE_INSENSITIVE_TEST @Value(_offset_y) = 1",delete,"BOOL_OP,AND,COMPOSITE_TEST,""""""1 AND 2 AND 3 AND 4"""""",TEST_CLAUSE,CASE_INSENSITIVE_TEST $(Features_to_print) CONTAINS natural
      CASE_INSENSITIVE_TEST @Value(_creation_instance) = 4
      CASE_INSENSITIVE_TEST @Value(_offset) = 1
      CASE_INSENSITIVE_TEST @Value(_offset_y) = 1",delete,"BOOL_OP,AND,COMPOSITE_TEST,""""""1 AND 2 AND 3 AND 4"""""",TEST_CLAUSE,CASE_INSENSITIVE_TEST $(Features_to_print) CONTAINS office
      CASE_INSENSITIVE_TEST @Value(_creation_instance) = 4
      CASE_INSENSITIVE_TEST @Value(_offset) = 2
      CASE_INSENSITIVE_TEST @Value(_offset_y) = 1",delete,"BOOL_OP,AND,COMPOSITE_TEST,""""""1 AND 2 AND 3 AND 4"""""",TEST_CLAUSE,CASE_INSENSITIVE_TEST $(Features_to_print) CONTAINS place
      CASE_INSENSITIVE_TEST @Value(_creation_instance) = 4
      CASE_INSENSITIVE_TEST @Value(_offset) = 3
      CASE_INSENSITIVE_TEST @Value(_offset_y) = 1",delete,"BOOL_OP,AND,COMPOSITE_TEST,""""""1 AND 2 AND 3 AND 4"""""",TEST_CLAUSE,CASE_INSENSITIVE_TEST $(Features_to_print) CONTAINS power
      CASE_INSENSITIVE_TEST @Value(_creation_instance) = 4
      CASE_INSENSITIVE_TEST @Value(_offset) = 4
      CASE_INSENSITIVE_TEST @Value(_offset_y) = 1",delete,"BOOL_OP,AND,COMPOSITE_TEST,""""""1 AND 2 AND 3 AND 4"""""",TEST_CLAUSE,CASE_INSENSITIVE_TEST $(Features_to_print) CONTAINS power
      CASE_INSENSITIVE_TEST @Value(_creation_instance) = 4
      CASE_INSENSITIVE_TEST @Value(_offset) = 5
      CASE_INSENSITIVE_TEST @Value(_offset_y) = 1",delete,"BOOL_OP,AND,COMPOSITE_TEST,""""""1 AND 2 AND 3 AND 4"""""",TEST_CLAUSE,CASE_INSENSITIVE_TEST $(Features_to_print) CONTAINS public_transport
      CASE_INSENSITIVE_TEST @Value(_creation_instance) = 4
      CASE_INSENSITIVE_TEST @Value(_offset) = 5
      CASE_INSENSITIVE_TEST @Value(_offset_y) = 1",delete,"BOOL_OP,AND,COMPOSITE_TEST,""""""1 AND 2 AND 3 AND 4"""""",TEST_CLAUSE,CASE_INSENSITIVE_TEST $(Features_to_print) CONTAINS railway
      CASE_INSENSITIVE_TEST @Value(_creation_instance) = 4
      CASE_INSENSITIVE_TEST @Value(_offset) = 6
      CASE_INSENSITIVE_TEST @Value(_offset_y) = 1",delete,"BOOL_OP,AND,COMPOSITE_TEST,""""""1 AND 2 AND 3 AND 4"""""",TEST_CLAUSE,CASE_INSENSITIVE_TEST $(Features_to_print) CONTAINS route
      CASE_INSENSITIVE_TEST @Value(_creation_instance) = 4
      CASE_INSENSITIVE_TEST @Value(_offset) = 0
      CASE_INSENSITIVE_TEST @Value(_offset_y) = 0",delete,"BOOL_OP,AND,COMPOSITE_TEST,""""""1 AND 2 AND 3 AND 4"""""",TEST_CLAUSE,CASE_INSENSITIVE_TEST $(Features_to_print) CONTAINS shop
      CASE_INSENSITIVE_TEST @Value(_creation_instance) = 4
      CASE_INSENSITIVE_TEST @Value(_offset) = 1
      CASE_INSENSITIVE_TEST @Value(_offset_y) = 0",delete,"BOOL_OP,AND,COMPOSITE_TEST,""""""1 AND 2 AND 3 AND 4"""""",TEST_CLAUSE,CASE_INSENSITIVE_TEST $(Features_to_print) CONTAINS sport
      CASE_INSENSITIVE_TEST @Value(_creation_instance) = 4
      CASE_INSENSITIVE_TEST @Value(_offset) = 2
      CASE_INSENSITIVE_TEST @Value(_offset_y) = 0",delete,"BOOL_OP,AND,COMPOSITE_TEST,""""""1 AND 2 AND 3 AND 4"""""",TEST_CLAUSE,CASE_INSENSITIVE_TEST $(Features_to_print) CONTAINS tourism
      CASE_INSENSITIVE_TEST @Value(_creation_instance) = 4
      CASE_INSENSITIVE_TEST @Value(_offset) = 3
      CASE_INSENSITIVE_TEST @Value(_offset_y) = 0",delete,"BOOL_OP,AND,COMPOSITE_TEST,""""""1 AND 2 AND 3 AND 4"""""",TEST_CLAUSE,CASE_INSENSITIVE_TEST $(Features_to_print) CONTAINS waterway
      CASE_INSENSITIVE_TEST @Value(_creation_instance) = 4
      CASE_INSENSITIVE_TEST @Value(_offset) = 4
      CASE_INSENSITIVE_TEST @Value(_offset_y) = 0",delete
    pass -> LineBuilder_3
LineBuilder_3
    ACCUM_INPUT_ATTRS = Use Attributes From One Feature
    GROUP_BY = _offset _offset_y
    REMOVE_DUPLICATES = No
    POLYGON -> PDFStyler_8
PDFStyler_8
    COLOR = 1,1,1
    FILL_COLOR = 1,1,1
    FILL_OPACITY = 1.00
    FONT = MS Shell Dlg 2,12,BOLD
    LINE_CAP_STYLE_PARAM = Butt Cap
    LINE_DASH_PHASE = 0
    LINE_JOIN_STYLE_PARAM = Miter Join
    LINE_MITER_LIMIT = 0.0
    LINE_WIDTH = 1
    OPACITY = 1.0
    PDFStyled -> PDFPageFormatter [Hide]
Creator_6
    GEOMTYPE = Geometry Object
    NUM = 8
    CREATED -> Cloner_4
Cloner_4
    COPIES = 7
    COPYATT = _offset
    COPY -> Cloner_2
Cloner_2
    COPIES = 4
    COPYATT = _offset_y
    COPY -> VertexCreator_2
VertexCreator_2
    MEASURE_TYPE = Continuous
    MISSING_VAL_MODE = Compute
    MODE_NAME = Add Point
    XVAL = FME_CONDITIONAL:DEFAULT_VALUE''BOOL_OP;OR;COMPOSITE_TEST;1 OR 2;TEST @Value(_creation_instance) = 0;TEST @Value(_creation_instance) = 4'0 + 4*@Value(_offset)'BOOL_OP;OR;COMPOSITE_TEST;1;TEST @Value(_creation_instance) = 1'1 + 4*@Value(_offset)'BOOL_OP;OR;COMPOSITE_TEST;1;TEST @Value(_creation_instance) = 2'1 + 4*@Value(_offset)'BOOL_OP;OR;COMPOSITE_TEST;1;TEST @Value(_creation_instance) = 3'0 + 4*@Value(_offset)'BOOL_OP;OR;COMPOSITE_TEST;1;TEST @Value(_creation_instance) = 5'1 +  4*@Value(_offset)'BOOL_OP;OR;COMPOSITE_TEST;1;TEST @Value(_creation_instance) = 6'0 + 4* @Value(_offset)'BOOL_OP;OR;COMPOSITE_TEST;1;TEST @Value(_creation_instance) = 7'1 + 4* @Value(_offset)'FME_NUM_CONDITIONS8___
    YVAL = FME_CONDITIONAL:DEFAULT_VALUE''BOOL_OP;OR;COMPOSITE_TEST;1 OR 2;TEST @Value(_creation_instance) = 0;TEST @Value(_creation_instance) = 4'1 + 2*@Value(_offset_y)'BOOL_OP;OR;COMPOSITE_TEST;1;TEST @Value(_creation_instance) = 1'1 + 2*@Value(_offset_y)'BOOL_OP;OR;COMPOSITE_TEST;1;TEST @Value(_creation_instance) = 2'0  + 2*@Value(_offset_y)'BOOL_OP;OR;COMPOSITE_TEST;1;TEST @Value(_creation_instance) = 3'0  + 2*@Value(_offset_y)'BOOL_OP;OR;COMPOSITE_TEST;1;TEST @Value(_creation_instance) = 5'0  + 2*@Value(_offset_y)'BOOL_OP;OR;COMPOSITE_TEST;1;TEST @Value(_creation_instance) = 6'0  + 2*@Value(_offset_y)'BOOL_OP;OR;COMPOSITE_TEST;1;TEST @Value(_creation_instance) = 7'1  + 2*@Value(_offset_y)'FME_NUM_CONDITIONS8___
    -> TestFilter_4
TestFilter_4
    DEFAULT_VALUE = pass
    TEST_LIST:
      "BOOL_OP,COMPOSITE,COMPOSITE_TEST,""""""1 AND ( 2 OR 3 ) AND ( 4 )"""""",TEST_CLAUSE,TEST @Value(_creation_instance) = 0
      TEST @Value(_offset) = 6
      TEST @Value(_offset) = 5
      TEST @Value(_offset_y) = 0",delete
    pass -> LineBuilder_2
LineBuilder_2
    ACCUM_INPUT_ATTRS = Use Attributes From One Feature
    GROUP_BY = _offset _offset_y
    REMOVE_DUPLICATES = No
    LINE -> PDFStyler_4
PDFStyler_4
    COLOR = 0,0,0
    FILL_COLOR = 0,0.333333,1
    FILL_OPACITY = 0.00
    FONT = MS Shell Dlg 2,12,BOLD
    LINE_CAP_STYLE_PARAM = Butt Cap
    LINE_DASH_PHASE = 0
    LINE_JOIN_STYLE_PARAM = Miter Join
    LINE_MITER_LIMIT = 0.0
    LINE_WIDTH = 1
    OPACITY = 1.0
    PDFStyled -> PDFPageFormatter [Features_preview]
North_5: Creator
    GEOM = <?xml version="1.0" encoding="US_ASCII" standalone="no" ?><geometry><text><point><coord x="0" y="0"/></point><textString>text</textString><textSize>10</textSize><textRotation>0</textRotation></text></geometry>
    GEOMTYPE = Geometry Object
    NUM = 4
    CREATED -> AttributeManager_12
AttributeManager_12
    ATTR_TABLE:
      SET_TO Coord = @GetWord($(GEOM),@Value(_creation_instance))
      SET_TO Coord_int = @Evaluate(@round(@Value(Coord),0))
      SET_TO Coord_min = @ReplaceString(@Value(Coord),., )
      SET_TO Coord_min = @GetWord(@Value(Coord_min),1)
      SET_TO Coord_min = 0.@Value(Coord_min)
      SET_TO Coord_min = @Evaluate(@Value(Coord_min)*60)
      SET_TO Coord_sec = @Value(Coord_min)
      SET_TO Coord_min = @Evaluate(@floor(@Value(Coord_min)))
      SET_TO Coord_sec = @Evaluate(@Value(Coord_sec)-@Value(Coord_min))
      SET_TO Coord_sec = @Evaluate(@Value(Coord_sec)*60)
      SET_TO Coord_sec = @Evaluate(@round(@Value(Coord_sec),0))
      SET_TO North_South = FME_CONDITIONAL:DEFAULT_VALUE'E'BOOL_OP;COMPOSITE;COMPOSITE_TEST;1 AND ( 2 OR 3 );TEST @Value(Coord_int) >= 0;TEST @Value(_creation_instance) = 1;TEST @Value(_creation_instance) = 3'N'BOOL_OP;COMPOSITE;COMPOSITE_TEST;1 AND ( 2 OR 3 );TEST @Value(Coord_int) < 0;TEST @Value(_creation_instance) = 1;TEST @Value(_creation_instance) = 3'S'BOOL_OP;COMPOSITE;COMPOSITE_TEST;1 AND ( 2 OR 3 );TEST @Value(Coord_int) < 0;TEST @Value(_creation_instance) = 0;TEST @Value(_creation_instance) = 2'W'FME_NUM_CONDITIONS4___
      SET_TO fme_text_string = @Value(Coord_int)°@Value(Coord_min)'@Value(Coord_sec)'' @Value(North_South)
    -> PDFStyler_26
PDFStyler_26
    COLOR = 0,0,0
    FILL_COLOR = 0,0,0
    FILL_OPACITY = 1.00
    FONT = MS Shell Dlg 2,12
    LINE_CAP_STYLE_PARAM = Butt Cap
    LINE_DASH_PHASE = 0
    LINE_JOIN_STYLE_PARAM = Miter Join
    LINE_MITER_LIMIT = 0.0
    LINE_WIDTH = 1.0
    OPACITY = 1.0
    PDFStyled -> TestFilter_7
TestFilter_7
    DEFAULT_VALUE = <UNFILTERED>
    TEST_LIST = "BOOL_OP,OR,COMPOSITE_TEST,""""""1"""""",TEST_CLAUSE,TEST @Value(_creation_instance) = 0",minLon,"BOOL_OP,OR,COMPOSITE_TEST,""""""1"""""",TEST_CLAUSE,TEST @Value(_creation_instance) = 1",minLat,"BOOL_OP,OR,COMPOSITE_TEST,""""""1"""""",TEST_CLAUSE,TEST @Value(_creation_instance) = 3",maxLon,"BOOL_OP,OR,COMPOSITE_TEST,""""""1"""""",TEST_CLAUSE,TEST @Value(_creation_instance) = 2",maxLat
    minLon -> PDFStyler_33
    minLon -> PDFStyler_29
    minLat -> PDFStyler_32
    maxLon -> PDFStyler_34
    maxLon -> PDFStyler_28
    maxLon -> PDFStyler_27
    maxLat -> PDFStyler_30
    maxLat -> PDFStyler_31
PDFStyler_32
    COLOR = 0,0,0
    FILL_COLOR = 0,0.333333,1
    FILL_OPACITY = 0.00
    FONT = MS Shell Dlg 2,12,BOLD
    LINE_CAP_STYLE_PARAM = Butt Cap
    LINE_DASH_PHASE = 0
    LINE_JOIN_STYLE_PARAM = Miter Join
    LINE_MITER_LIMIT = 0.0
    LINE_WIDTH = 1
    OPACITY = 1.0
PDFStyler_33
    COLOR = 0,0,0
    FILL_COLOR = 0,0.333333,1
    FILL_OPACITY = 0.00
    FONT = MS Shell Dlg 2,12,BOLD
    LINE_CAP_STYLE_PARAM = Butt Cap
    LINE_DASH_PHASE = 0
    LINE_JOIN_STYLE_PARAM = Miter Join
    LINE_MITER_LIMIT = 0.0
    LINE_WIDTH = 1
    OPACITY = 1.0
PDFStyler_29
    COLOR = 0,0,0
    FILL_COLOR = 0,0.333333,1
    FILL_OPACITY = 0.00
    FONT = MS Shell Dlg 2,12,BOLD
    LINE_CAP_STYLE_PARAM = Butt Cap
    LINE_DASH_PHASE = 0
    LINE_JOIN_STYLE_PARAM = Miter Join
    LINE_MITER_LIMIT = 0.0
    LINE_WIDTH = 1
    OPACITY = 1.0
PDFStyler_27
    COLOR = 0,0,0
    FILL_COLOR = 0,0.333333,1
    FILL_OPACITY = 0.00
    FONT = MS Shell Dlg 2,12,BOLD
    LINE_CAP_STYLE_PARAM = Butt Cap
    LINE_DASH_PHASE = 0
    LINE_JOIN_STYLE_PARAM = Miter Join
    LINE_MITER_LIMIT = 0.0
    LINE_WIDTH = 1
    OPACITY = 1.0
PDFStyler_34
    COLOR = 0,0,0
    FILL_COLOR = 0,0.333333,1
    FILL_OPACITY = 0.00
    FONT = MS Shell Dlg 2,12,BOLD
    LINE_CAP_STYLE_PARAM = Butt Cap
    LINE_DASH_PHASE = 0
    LINE_JOIN_STYLE_PARAM = Miter Join
    LINE_MITER_LIMIT = 0.0
    LINE_WIDTH = 1
    OPACITY = 1.0
PDFStyler_28
    COLOR = 0,0,0
    FILL_COLOR = 0,0.333333,1
    FILL_OPACITY = 0.00
    FONT = MS Shell Dlg 2,12,BOLD
    LINE_CAP_STYLE_PARAM = Butt Cap
    LINE_DASH_PHASE = 0
    LINE_JOIN_STYLE_PARAM = Miter Join
    LINE_MITER_LIMIT = 0.0
    LINE_WIDTH = 1
    OPACITY = 1.0
PDFStyler_30
    COLOR = 0,0,0
    FILL_COLOR = 0,0.333333,1
    FILL_OPACITY = 0.00
    FONT = MS Shell Dlg 2,12,BOLD
    LINE_CAP_STYLE_PARAM = Butt Cap
    LINE_DASH_PHASE = 0
    LINE_JOIN_STYLE_PARAM = Miter Join
    LINE_MITER_LIMIT = 0.0
    LINE_WIDTH = 1
    OPACITY = 1.0
PDFStyler_31
    COLOR = 0,0,0
    FILL_COLOR = 0,0.333333,1
    FILL_OPACITY = 0.00
    FONT = MS Shell Dlg 2,12,BOLD
    LINE_CAP_STYLE_PARAM = Butt Cap
    LINE_DASH_PHASE = 0
    LINE_JOIN_STYLE_PARAM = Miter Join
    LINE_MITER_LIMIT = 0.0
    LINE_WIDTH = 1
    OPACITY = 1.0
Creator_10
    GEOMTYPE = Geometry Object
    NUM = 5
    CREATED -> VertexCreator_14
VertexCreator_14
    MEASURE_TYPE = Continuous
    MISSING_VAL_MODE = Compute
    MODE_NAME = Add Point
    XVAL = FME_CONDITIONAL:DEFAULT_VALUE''BOOL_OP;OR;COMPOSITE_TEST;1 OR 2 OR 3;TEST @Value(_creation_instance) = 0;TEST @Value(_creation_instance) = 4;TEST @Value(_creation_instance) = 3'0'BOOL_OP;OR;COMPOSITE_TEST;1 OR 2;TEST @Value(_creation_instance) = 1;TEST @Value(_creation_instance) = 2'1'FME_NUM_CONDITIONS3___
    YVAL = FME_CONDITIONAL:DEFAULT_VALUE''BOOL_OP;OR;COMPOSITE_TEST;1 OR 2 OR 3;TEST @Value(_creation_instance) = 0;TEST @Value(_creation_instance) = 4;TEST @Value(_creation_instance) = 1'1'BOOL_OP;OR;COMPOSITE_TEST;1 OR 2;TEST @Value(_creation_instance) = 2;TEST @Value(_creation_instance) = 3'0'FME_NUM_CONDITIONS3___
    -> LineBuilder_10
LineBuilder_10
    ACCUM_INPUT_ATTRS = Use Attributes From One Feature
    REMOVE_DUPLICATES = No
    POLYGON -> PDFStyler_25
PDFStyler_25
    COLOR = 0,0,0
    FILL_COLOR = 0,0.333333,1
    FILL_OPACITY = 0.00
    FONT = MS Shell Dlg 2,12,BOLD
    LINE_CAP_STYLE_PARAM = Butt Cap
    LINE_DASH_PHASE = 0
    LINE_JOIN_STYLE_PARAM = Miter Join
    LINE_MITER_LIMIT = 0.0
    LINE_WIDTH = 1
    OPACITY = 1.0
North_3: Creator
    GEOM = <?xml version="1.0" encoding="US_ASCII" standalone="no" ?><geometry><text><point><coord x="0" y="0"/></point><textString>Am</textString><textSize>10</textSize><textRotation>0</textRotation></text></geometry>
    GEOMTYPE = Geometry Object
    NUM = 26
    CREATED -> AttributeManager_3
AttributeManager_3
    ATTR_TABLE:
      SET_TO fme_text_string = FME_CONDITIONAL:DEFAULT_VALUE'_FME_NO_OP_'BOOL_OP;OR;COMPOSITE_TEST;1;TEST @Value(_creation_instance) = 0'Ai'BOOL_OP;OR;COMPOSITE_TEST;1;TEST @Value(_creation_instance) = 1'Ao'BOOL_OP;OR;COMPOSITE_TEST;1;TEST @Value(_creation_instance) = 2'Ae'BOOL_OP;OR;COMPOSITE_TEST;1;TEST @Value(_creation_instance) = 3'Ba'BOOL_OP;OR;COMPOSITE_TEST;1;TEST @Value(_creation_instance) = 4'Bo'BOOL_OP;OR;COMPOSITE_TEST;1;TEST @Value(_creation_instance) = 5'Bu'BOOL_OP;OR;COMPOSITE_TEST;1;TEST @Value(_creation_instance) = 6'Ca'BOOL_OP;OR;COMPOSITE_TEST;1;TEST @Value(_creation_instance) = 7'Em'BOOL_OP;OR;COMPOSITE_TEST;1;TEST @Value(_creation_instance) = 8'Ge'BOOL_OP;OR;COMPOSITE_TEST;1;TEST @Value(_creation_instance) = 9'Hg'BOOL_OP;OR;COMPOSITE_TEST;1;TEST @Value(_creation_instance) = 10'Ht'BOOL_OP;OR;COMPOSITE_TEST;1;TEST @Value(_creation_instance) = 11'La'BOOL_OP;OR;COMPOSITE_TEST;1;TEST @Value(_creation_instance) = 12'Le'BOOL_OP;OR;COMPOSITE_TEST;1;TEST @Value(_creation_instance) = 13'Mm'BOOL_OP;OR;COMPOSITE_TEST;1;TEST @Value(_creation_instance) = 14'Mi'BOOL_OP;OR;COMPOSITE_TEST;1;TEST @Value(_creation_instance) = 15'Na'BOOL_OP;OR;COMPOSITE_TEST;1;TEST @Value(_creation_instance) = 16'Of'BOOL_OP;OR;COMPOSITE_TEST;1;TEST @Value(_creation_instance) = 17'Pl'BOOL_OP;OR;COMPOSITE_TEST;1;TEST @Value(_creation_instance) = 18'Po'BOOL_OP;OR;COMPOSITE_TEST;1;TEST @Value(_creation_instance) = 19'Pt'BOOL_OP;OR;COMPOSITE_TEST;1;TEST @Value(_creation_instance) = 20'Ra'BOOL_OP;OR;COMPOSITE_TEST;1;TEST @Value(_creation_instance) = 21'Ro'BOOL_OP;OR;COMPOSITE_TEST;1;TEST @Value(_creation_instance) = 22'Sh'BOOL_OP;OR;COMPOSITE_TEST;1;TEST @Value(_creation_instance) = 23'Sp'BOOL_OP;OR;COMPOSITE_TEST;1;TEST @Value(_creation_instance) = 24'To'BOOL_OP;OR;COMPOSITE_TEST;1;TEST @Value(_creation_instance) = 25'Wa'FME_NUM_CONDITIONS27___
      SET_TO offset_y = FME_CONDITIONAL:DEFAULT_VALUE'_FME_NO_OP_'BOOL_OP;OR;COMPOSITE_TEST;1;NUM_TEST @Value(_creation_instance) RANGE [0,6]'0'BOOL_OP;OR;COMPOSITE_TEST;1;NUM_TEST @Value(_creation_instance) RANGE [7,13]'1'BOOL_OP;OR;COMPOSITE_TEST;1;NUM_TEST @Value(_creation_instance) RANGE [14,20]'2'BOOL_OP;OR;COMPOSITE_TEST;1;NUM_TEST @Value(_creation_instance) RANGE [21,26]'3'FME_NUM_CONDITIONS5___
      SET_TO offset_x = FME_CONDITIONAL:DEFAULT_VALUE'_FME_NO_OP_'BOOL_OP;OR;COMPOSITE_TEST;1;TEST @Value(_creation_instance) = 0'0'BOOL_OP;OR;COMPOSITE_TEST;1;TEST @Value(_creation_instance) = 7'0'BOOL_OP;OR;COMPOSITE_TEST;1;TEST @Value(_creation_instance) = 14'0'BOOL_OP;OR;COMPOSITE_TEST;1;TEST @Value(_creation_instance) = 21'0'BOOL_OP;OR;COMPOSITE_TEST;1;TEST @Value(_creation_instance) = 1'1'BOOL_OP;OR;COMPOSITE_TEST;1;TEST @Value(_creation_instance) = 8'1'BOOL_OP;OR;COMPOSITE_TEST;1;TEST @Value(_creation_instance) = 15'1'BOOL_OP;OR;COMPOSITE_TEST;1;TEST @Value(_creation_instance) = 22'1'BOOL_OP;OR;COMPOSITE_TEST;1;TEST @Value(_creation_instance) = 2'2'BOOL_OP;OR;COMPOSITE_TEST;1;TEST @Value(_creation_instance) = 9'2'BOOL_OP;OR;COMPOSITE_TEST;1;TEST @Value(_creation_instance) = 16'2'BOOL_OP;OR;COMPOSITE_TEST;1;TEST @Value(_creation_instance) = 23'2'BOOL_OP;OR;COMPOSITE_TEST;1;TEST @Value(_creation_instance) = 3'3'BOOL_OP;OR;COMPOSITE_TEST;1;TEST @Value(_creation_instance) = 10'3'BOOL_OP;OR;COMPOSITE_TEST;1;TEST @Value(_creation_instance) = 17'3'BOOL_OP;OR;COMPOSITE_TEST;1;TEST @Value(_creation_instance) = 24'3'BOOL_OP;OR;COMPOSITE_TEST;1;TEST @Value(_creation_instance) = 4'4'BOOL_OP;OR;COMPOSITE_TEST;1;TEST @Value(_creation_instance) = 11'4'BOOL_OP;OR;COMPOSITE_TEST;1;TEST @Value(_creation_instance) = 18'4'BOOL_OP;OR;COMPOSITE_TEST;1;TEST @Value(_creation_instance) = 25'4'BOOL_OP;OR;COMPOSITE_TEST;1;TEST @Value(_creation_instance) = 5'5'BOOL_OP;OR;COMPOSITE_TEST;1;TEST @Value(_creation_instance) = 12'5'BOOL_OP;OR;COMPOSITE_TEST;1;TEST @Value(_creation_instance) = 19'5'BOOL_OP;OR;COMPOSITE_TEST;1;TEST @Value(_creation_instance) = 26'5'BOOL_OP;OR;COMPOSITE_TEST;1;TEST @Value(_creation_instance) = 6'6'BOOL_OP;OR;COMPOSITE_TEST;1;TEST @Value(_creation_instance) = 13'6'BOOL_OP;OR;COMPOSITE_TEST;1;TEST @Value(_creation_instance) = 20'6'FME_NUM_CONDITIONS28___
    -> Offsetter
Offsetter
    MODE = Cartesian Coordinate
    XOFF = 30 * @Value(offset_x)
    YOFF = - 14.42 * @Value(offset_y)
    ZOFF = 0
    OFFSET -> PDFStyler_5
PDFStyler_5
    COLOR = 0,0,0
    FILL_COLOR = 0,0,0
    FILL_OPACITY = 1.00
    FONT = MS Shell Dlg 2,12,BOLD
    LINE_CAP_STYLE_PARAM = Butt Cap
    LINE_DASH_PHASE = 0
    LINE_JOIN_STYLE_PARAM = Miter Join
    LINE_MITER_LIMIT = 0.0
    LINE_WIDTH = 1.0
    OPACITY = 1.0
    PDFStyled -> PDFPageFormatter [Tf]
North_8: Creator
    GEOM = <?xml version="1.0" encoding="US_ASCII" standalone="no" ?><geometry><text><point><coord x="0" y="0"/></point><textString>Population density</textString><textSize>10</textSize><textRotation>0</textRotation></text></geometry>
    GEOMTYPE = Geometry Object
    NUM = 1
    CREATED -> PDFStyler_37
PDFStyler_37
    COLOR = FME_CONDITIONAL:DEFAULT_VALUE'0,0,0'BOOL_OP;OR;COMPOSITE_TEST;1;CASE_INSENSITIVE_TEST $(LAYER_TYPE_2_MAP) CONTAINS PopDens'0,0,1'FME_NUM_CONDITIONS2___
    FILL_COLOR = 0,0,0
    FILL_OPACITY = 1.00
    FONT = FME_CONDITIONAL:DEFAULT_VALUE'MS Shell Dlg 2,9'BOOL_OP;OR;COMPOSITE_TEST;1;CASE_INSENSITIVE_TEST $(LAYER_TYPE_2_MAP) CONTAINS PopDens'MS Shell Dlg 2,9,BOLD,UNDERLINE'FME_NUM_CONDITIONS2___
    LINE_CAP_STYLE_PARAM = Butt Cap
    LINE_DASH_PHASE = 0
    LINE_JOIN_STYLE_PARAM = Miter Join
    LINE_MITER_LIMIT = 0.0
    LINE_WIDTH = 1.0
    OPACITY = 1.0
    PDFStyled -> PDFPageFormatter [Population Density]
North_7: Creator
    GEOM = <?xml version="1.0" encoding="US_ASCII" standalone="no" ?><geometry><text><point><coord x="0" y="0"/></point><textString>Contour Lines (20m)</textString><textSize>10</textSize><textRotation>0</textRotation></text></geometry>
    GEOMTYPE = Geometry Object
    NUM = 1
    CREATED -> PDFStyler_36
PDFStyler_36
    COLOR = FME_CONDITIONAL:DEFAULT_VALUE'0,0,0'BOOL_OP;OR;COMPOSITE_TEST;1;CASE_INSENSITIVE_TEST $(LAYER_TYPE_2_MAP) CONTAINS ContourLines'0,0,1'FME_NUM_CONDITIONS2___
    FILL_COLOR = 0,0,0
    FILL_OPACITY = 1.00
    FONT = FME_CONDITIONAL:DEFAULT_VALUE'MS Shell Dlg 2,9'BOOL_OP;OR;COMPOSITE_TEST;1;CASE_INSENSITIVE_TEST $(LAYER_TYPE_2_MAP) CONTAINS ContourLines'MS Shell Dlg 2,9,BOLD, UNDERLINE'FME_NUM_CONDITIONS2___
    LINE_CAP_STYLE_PARAM = Butt Cap
    LINE_DASH_PHASE = 0
    LINE_JOIN_STYLE_PARAM = Miter Join
    LINE_MITER_LIMIT = 0.0
    LINE_WIDTH = 1.0
    OPACITY = 1.0
    PDFStyled -> PDFPageFormatter [contour]
North_6: Creator
    GEOM = <?xml version="1.0" encoding="US_ASCII" standalone="no" ?><geometry><text><point><coord x="0" y="0"/></point><textString>DEM</textString><textSize>10</textSize><textRotation>0</textRotation></text></geometry>
    GEOMTYPE = Geometry Object
    NUM = 1
    CREATED -> PDFStyler_35
PDFStyler_35
    COLOR = FME_CONDITIONAL:DEFAULT_VALUE'0,0,0'BOOL_OP;OR;COMPOSITE_TEST;1;CASE_INSENSITIVE_TEST $(LAYER_TYPE_2_MAP) CONTAINS DEM'0,0,1'FME_NUM_CONDITIONS2___
    FILL_COLOR = 0,0,0
    FILL_OPACITY = 1.00
    FONT = FME_CONDITIONAL:DEFAULT_VALUE'MS Shell Dlg 2,9'BOOL_OP;OR;COMPOSITE_TEST;1;CASE_INSENSITIVE_TEST $(LAYER_TYPE_2_MAP) CONTAINS DEM'MS Shell Dlg 2,9,BOLD,UNDERLINE'FME_NUM_CONDITIONS2___
    LINE_CAP_STYLE_PARAM = Butt Cap
    LINE_DASH_PHASE = 0
    LINE_JOIN_STYLE_PARAM = Miter Join
    LINE_MITER_LIMIT = 0.0
    LINE_WIDTH = 1.0
    OPACITY = 1.0
    PDFStyled -> PDFPageFormatter [OSM]
North_4: Creator
    GEOM = <?xml version="1.0" encoding="US_ASCII" standalone="no" ?><geometry><text><point><coord x="0" y="0"/></point><textString>Printed OSM features:</textString><textSize>10</textSize><textRotation>0</textRotation></text></geometry>
    GEOMTYPE = Geometry Object
    NUM = 1
    CREATED -> PDFStyler_19
PDFStyler_19
    COLOR = 0,0,0
    FILL_COLOR = 0,0,0
    FILL_OPACITY = 1.00
    FONT = MS Shell Dlg 2,12
    LINE_CAP_STYLE_PARAM = Butt Cap
    LINE_DASH_PHASE = 0
    LINE_JOIN_STYLE_PARAM = Miter Join
    LINE_MITER_LIMIT = 0.0
    LINE_WIDTH = 1.0
    OPACITY = 1.0
    PDFStyled -> PDFPageFormatter [PF]

Bookmark: OSM layer
Creator_5
    GEOMTYPE = Geometry Object
    NUM = $(Number_of_features)
    CREATED -> TestFilter_14
TestFilter_14
    DEFAULT_VALUE = <UNFILTERED>
    TEST_LIST = "BOOL_OP,OR,COMPOSITE_TEST,""""""1"""""",TEST_CLAUSE,CASE_INSENSITIVE_TEST $(LAYER_TYPE_2_MAP) CONTAINS OSM",ok
    ok -> AttributeManager
AttributeManager
    ATTR_TABLE:
      SET_TO attribute2print = @GetWord($(Features_to_print),@Value(_creation_instance))
      SET_TO test = $(Layer_feature)_$(ISO)\01_OSM_shp\@Value(attribute2print)\$(DATE)_$(ISO)_@Value(attribute2print)_line.shp
    -> FeatureReader_4 [INITIATOR]
    -> FeatureReader_5 [INITIATOR]
    -> FeatureReader_6 [INITIATOR]
FeatureReader_4
    ATTR_ACCUM_MODE = Merge Initiator and Result
    ATTR_CONFLICT_RES = Use Result
    ATTR_IGNORE_NULLS = No
    COMBINE_GEOM = Use Result
    DATASET = $(Layer_feature)_$(ISO)\01_OSM\@Value(attribute2print)\$(DATE)_$(ISO)_@Value(attribute2print)_line.shp
    FORMAT = SHAPEFILE
    INTERACT = <No Spatial Filter>
    OUTPUT_FEATURES_DISPLAY = Schema and Data Features
    SHAPEFILE_DONUT_DETECTION = ORIENTATION
    SHAPEFILE_ENCODING = fme-source-encoding
    SHAPEFILE_MEASURES_AS_Z = No
    SHAPEFILE_NUMERIC_TYPE_ATTRIBUTE_HANDLING = STANDARD_TYPES
    SHAPEFILE_READ_BLANK_AS = MISSING
    SHAPEFILE_REPORT_BAD_GEOMETRY = No
    SHAPEFILE_TRIM_PRECEDING_SPACES = Yes
    SHAPEFILE_USE_SEARCH_ENVELOPE = NO
    <OTHER> -> Clipper_4 [CLIPPEE]
    <REJECTED> -> Logger
FeatureReader_5
    ATTR_ACCUM_MODE = Merge Initiator and Result
    ATTR_CONFLICT_RES = Use Result
    ATTR_IGNORE_NULLS = No
    COMBINE_GEOM = Use Result
    DATASET = $(Layer_feature)_$(ISO)\01_OSM\@Value(attribute2print)\$(DATE)_$(ISO)_@Value(attribute2print)_point.shp
    FORMAT = SHAPEFILE
    INTERACT = <No Spatial Filter>
    OUTPUT_FEATURES_DISPLAY = Schema and Data Features
    SHAPEFILE_DONUT_DETECTION = ORIENTATION
    SHAPEFILE_ENCODING = fme-source-encoding
    SHAPEFILE_MEASURES_AS_Z = No
    SHAPEFILE_NUMERIC_TYPE_ATTRIBUTE_HANDLING = STANDARD_TYPES
    SHAPEFILE_READ_BLANK_AS = MISSING
    SHAPEFILE_REPORT_BAD_GEOMETRY = No
    SHAPEFILE_TRIM_PRECEDING_SPACES = Yes
    SHAPEFILE_USE_SEARCH_ENVELOPE = NO
    <OTHER> -> Clipper_4 [CLIPPEE]
    <REJECTED> -> Logger
FeatureReader_6
    ATTR_ACCUM_MODE = Merge Initiator and Result
    ATTR_CONFLICT_RES = Use Result
    ATTR_IGNORE_NULLS = No
    COMBINE_GEOM = Use Result
    DATASET = $(Layer_feature)_$(ISO)\01_OSM\@Value(attribute2print)\$(DATE)_$(ISO)_@Value(attribute2print)_polygone.shp
    FORMAT = SHAPEFILE
    INTERACT = <No Spatial Filter>
    OUTPUT_FEATURES_DISPLAY = Schema and Data Features
    SHAPEFILE_DONUT_DETECTION = ORIENTATION
    SHAPEFILE_ENCODING = fme-source-encoding
    SHAPEFILE_MEASURES_AS_Z = No
    SHAPEFILE_NUMERIC_TYPE_ATTRIBUTE_HANDLING = STANDARD_TYPES
    SHAPEFILE_READ_BLANK_AS = MISSING
    SHAPEFILE_REPORT_BAD_GEOMETRY = No
    SHAPEFILE_TRIM_PRECEDING_SPACES = Yes
    SHAPEFILE_USE_SEARCH_ENVELOPE = NO
    <OTHER> -> Clipper_4 [CLIPPEE]
    <REJECTED> -> Logger
Clipper_4
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    INSIDE -> AttributeCreator_6
    <REJECTED> -> Logger
AttributeCreator_6
    ATTR_TABLE:
      SET_TO _order = 4
      SET_TO pdf_point_width = 1.5
      SET_TO color = FME_CONDITIONAL:DEFAULT_VALUE'0,0,0'BOOL_OP;OR;COMPOSITE_TEST;1;TEST @Value(attribute2print) = highway'1,0.33,0'BOOL_OP;OR;COMPOSITE_TEST;1;TEST @Value(attribute2print) = boundary'0,0,0'BOOL_OP;OR;COMPOSITE_TEST;1;TEST @Value(attribute2print) = building'1,0,0'BOOL_OP;OR;COMPOSITE_TEST;1;TEST @Value(attribute2print) = shop'0.262,0.2039,0.4862'BOOL_OP;OR;COMPOSITE_TEST;1;TEST @Value(attribute2print) = aerialway'1,0.2,0.2'BOOL_OP;OR;COMPOSITE_TEST;1;TEST @Value(attribute2print) = aeroway'0.251,0.251,0.251'BOOL_OP;OR;COMPOSITE_TEST;1;TEST @Value(attribute2print) = amenity'0.6,0.298,0'BOOL_OP;OR;COMPOSITE_TEST;1;TEST @Value(attribute2print) = barrier'0.2,0.098,0'BOOL_OP;OR;COMPOSITE_TEST;1;TEST @Value(attribute2print) = craft'0.6901,0.7411,0.0117'BOOL_OP;OR;COMPOSITE_TEST;1;TEST @Value(attribute2print) = emergency'0.9765,0.4392,0.34901'BOOL_OP;OR;COMPOSITE_TEST;1;TEST @Value(attribute2print) = geological'0.235,0.623,0.584'BOOL_OP;OR;COMPOSITE_TEST;1;TEST @Value(attribute2print) = landuse'0.2353,0.2,0'BOOL_OP;OR;COMPOSITE_TEST;1;TEST @Value(attribute2print) = historic'0.4353,0.5686,0.4431'BOOL_OP;OR;COMPOSITE_TEST;1;TEST @Value(attribute2print) = leisure'0.08235,0.2784,0.9137'BOOL_OP;OR;COMPOSITE_TEST;1;TEST @Value(attribute2print) = man_made'0.1568,0.8471,0.4353'BOOL_OP;OR;COMPOSITE_TEST;1;TEST @Value(attribute2print) = military'0.1804,0.2,0.03921'BOOL_OP;OR;COMPOSITE_TEST;1;TEST @Value(attribute2print) = natural'0,1,0'BOOL_OP;OR;COMPOSITE_TEST;1;TEST @Value(attribute2print) = office'0.4,0,0.2'BOOL_OP;OR;COMPOSITE_TEST;1;TEST @Value(attribute2print) = place'0,0,0'BOOL_OP;OR;COMPOSITE_TEST;1;TEST @Value(attribute2print) = power'0.5,0.5,0.5'BOOL_OP;OR;COMPOSITE_TEST;1;TEST @Value(attribute2print) = public_transport'0.2,0,0.098'BOOL_OP;OR;COMPOSITE_TEST;1;TEST @Value(attribute2print) = railway'1,0,0.902'BOOL_OP;OR;COMPOSITE_TEST;1;TEST @Value(attribute2print) = route'1,1,0'BOOL_OP;OR;COMPOSITE_TEST;1;TEST @Value(attribute2print) = shop'0.2627,0.239,0.486'BOOL_OP;OR;COMPOSITE_TEST;1;TEST @Value(attribute2print) = sport'0.5843,0.5,0.4196'BOOL_OP;OR;COMPOSITE_TEST;1;TEST @Value(attribute2print) = tourism'1,0.8,0.8'BOOL_OP;OR;COMPOSITE_TEST;1;TEST @Value(attribute2print) = waterway'0,0,1'FME_NUM_CONDITIONS28___
      SET_TO line_style = FME_CONDITIONAL:DEFAULT_VALUE''BOOL_OP;OR;COMPOSITE_TEST;1;TEST @Value(attribute2print) = highway''BOOL_OP;OR;COMPOSITE_TEST;1;TEST @Value(attribute2print) = boundary'2 3 2 3'BOOL_OP;OR;COMPOSITE_TEST;1;TEST @Value(attribute2print) = building''BOOL_OP;OR;COMPOSITE_TEST;1;TEST @Value(attribute2print) = shop''BOOL_OP;OR;COMPOSITE_TEST;1;TEST @Value(attribute2print) = aerialway''BOOL_OP;OR;COMPOSITE_TEST;1;TEST @Value(attribute2print) = aeroway''BOOL_OP;OR;COMPOSITE_TEST;1;TEST @Value(attribute2print) = amenity''BOOL_OP;OR;COMPOSITE_TEST;1;TEST @Value(attribute2print) = barrier''BOOL_OP;OR;COMPOSITE_TEST;1;TEST @Value(attribute2print) = craft''BOOL_OP;OR;COMPOSITE_TEST;1;TEST @Value(attribute2print) = emergency''BOOL_OP;OR;COMPOSITE_TEST;1;TEST @Value(attribute2print) = geological''BOOL_OP;OR;COMPOSITE_TEST;1;TEST @Value(attribute2print) = landuse''BOOL_OP;OR;COMPOSITE_TEST;1;TEST @Value(attribute2print) = historic''BOOL_OP;OR;COMPOSITE_TEST;1;TEST @Value(attribute2print) = leisure''BOOL_OP;OR;COMPOSITE_TEST;1;TEST @Value(attribute2print) = man_made''BOOL_OP;OR;COMPOSITE_TEST;1;TEST @Value(attribute2print) = military''BOOL_OP;OR;COMPOSITE_TEST;1;TEST @Value(attribute2print) = natural''BOOL_OP;OR;COMPOSITE_TEST;1;TEST @Value(attribute2print) = office''BOOL_OP;OR;COMPOSITE_TEST;1;TEST @Value(attribute2print) = place''BOOL_OP;OR;COMPOSITE_TEST;1;TEST @Value(attribute2print) = power'2 3 2 3'BOOL_OP;OR;COMPOSITE_TEST;1;TEST @Value(attribute2print) = public_transport''BOOL_OP;OR;COMPOSITE_TEST;1;TEST @Value(attribute2print) = railway'2 3 2 3'BOOL_OP;OR;COMPOSITE_TEST;1;TEST @Value(attribute2print) = route''BOOL_OP;OR;COMPOSITE_TEST;1;TEST @Value(attribute2print) = shop''BOOL_OP;OR;COMPOSITE_TEST;1;TEST @Value(attribute2print) = sport''BOOL_OP;OR;COMPOSITE_TEST;1;TEST @Value(attribute2print) = tourism''BOOL_OP;OR;COMPOSITE_TEST;1;TEST @Value(attribute2print) = waterway''FME_NUM_CONDITIONS28___
      SET_TO line_phase = FME_CONDITIONAL:DEFAULT_VALUE'0'BOOL_OP;OR;COMPOSITE_TEST;1;TEST @Value(attribute2print) = highway'0'BOOL_OP;OR;COMPOSITE_TEST;1;TEST @Value(attribute2print) = boundary'10'BOOL_OP;OR;COMPOSITE_TEST;1;TEST @Value(attribute2print) = building'0'BOOL_OP;OR;COMPOSITE_TEST;1;TEST @Value(attribute2print) = shop'0'BOOL_OP;OR;COMPOSITE_TEST;1;TEST @Value(attribute2print) = aerialway'0'BOOL_OP;OR;COMPOSITE_TEST;1;TEST @Value(attribute2print) = aeroway'0'BOOL_OP;OR;COMPOSITE_TEST;1;TEST @Value(attribute2print) = amenity'0'BOOL_OP;OR;COMPOSITE_TEST;1;TEST @Value(attribute2print) = barrier'0'BOOL_OP;OR;COMPOSITE_TEST;1;TEST @Value(attribute2print) = craft'0'BOOL_OP;OR;COMPOSITE_TEST;1;TEST @Value(attribute2print) = emergency'0'BOOL_OP;OR;COMPOSITE_TEST;1;TEST @Value(attribute2print) = geological'0'BOOL_OP;OR;COMPOSITE_TEST;1;TEST @Value(attribute2print) = landuse'0'BOOL_OP;OR;COMPOSITE_TEST;1;TEST @Value(attribute2print) = historic'0'BOOL_OP;OR;COMPOSITE_TEST;1;TEST @Value(attribute2print) = leisure'0'BOOL_OP;OR;COMPOSITE_TEST;1;TEST @Value(attribute2print) = man_made'0'BOOL_OP;OR;COMPOSITE_TEST;1;TEST @Value(attribute2print) = military'0'BOOL_OP;OR;COMPOSITE_TEST;1;TEST @Value(attribute2print) = natural'0'BOOL_OP;OR;COMPOSITE_TEST;1;TEST @Value(attribute2print) = office'0'BOOL_OP;OR;COMPOSITE_TEST;1;TEST @Value(attribute2print) = place'0'BOOL_OP;OR;COMPOSITE_TEST;1;TEST @Value(attribute2print) = power'10'BOOL_OP;OR;COMPOSITE_TEST;1;TEST @Value(attribute2print) = public_transport'0'BOOL_OP;OR;COMPOSITE_TEST;1;TEST @Value(attribute2print) = railway'10'BOOL_OP;OR;COMPOSITE_TEST;1;TEST @Value(attribute2print) = route'0'BOOL_OP;OR;COMPOSITE_TEST;1;TEST @Value(attribute2print) = shop'0'BOOL_OP;OR;COMPOSITE_TEST;1;TEST @Value(attribute2print) = sport'0'BOOL_OP;OR;COMPOSITE_TEST;1;TEST @Value(attribute2print) = tourism'0'BOOL_OP;OR;COMPOSITE_TEST;1;TEST @Value(attribute2print) = waterway'0'FME_NUM_CONDITIONS28___
      SET_TO line_width = FME_CONDITIONAL:DEFAULT_VALUE'1'BOOL_OP;OR;COMPOSITE_TEST;1;TEST @Value(attribute2print) = highway'2'BOOL_OP;OR;COMPOSITE_TEST;1;TEST @Value(attribute2print) = boundary'4'BOOL_OP;OR;COMPOSITE_TEST;1;TEST @Value(attribute2print) = building'1'BOOL_OP;OR;COMPOSITE_TEST;1;TEST @Value(attribute2print) = shop'2'BOOL_OP;OR;COMPOSITE_TEST;1;TEST @Value(attribute2print) = aerialway'2'BOOL_OP;OR;COMPOSITE_TEST;1;TEST @Value(attribute2print) = aeroway'2'BOOL_OP;OR;COMPOSITE_TEST;1;TEST @Value(attribute2print) = amenity'2'BOOL_OP;OR;COMPOSITE_TEST;1;TEST @Value(attribute2print) = barrier'2'BOOL_OP;OR;COMPOSITE_TEST;1;TEST @Value(attribute2print) = craft'2'BOOL_OP;OR;COMPOSITE_TEST;1;TEST @Value(attribute2print) = emergency'2'BOOL_OP;OR;COMPOSITE_TEST;1;TEST @Value(attribute2print) = geological'1'BOOL_OP;OR;COMPOSITE_TEST;1;TEST @Value(attribute2print) = landuse'1'BOOL_OP;OR;COMPOSITE_TEST;1;TEST @Value(attribute2print) = historic'2'BOOL_OP;OR;COMPOSITE_TEST;1;TEST @Value(attribute2print) = leisure'2'BOOL_OP;OR;COMPOSITE_TEST;1;TEST @Value(attribute2print) = man_made'2'BOOL_OP;OR;COMPOSITE_TEST;1;TEST @Value(attribute2print) = military'2'BOOL_OP;OR;COMPOSITE_TEST;1;TEST @Value(attribute2print) = natural'1'BOOL_OP;OR;COMPOSITE_TEST;1;TEST @Value(attribute2print) = office'2'BOOL_OP;OR;COMPOSITE_TEST;1;TEST @Value(attribute2print) = place'4'BOOL_OP;OR;COMPOSITE_TEST;1;TEST @Value(attribute2print) = power'2'BOOL_OP;OR;COMPOSITE_TEST;1;TEST @Value(attribute2print) = public_transport'2'BOOL_OP;OR;COMPOSITE_TEST;1;TEST @Value(attribute2print) = railway'2'BOOL_OP;OR;COMPOSITE_TEST;1;TEST @Value(attribute2print) = route'2'BOOL_OP;OR;COMPOSITE_TEST;1;TEST @Value(attribute2print) = shop'2'BOOL_OP;OR;COMPOSITE_TEST;1;TEST @Value(attribute2print) = sport'2'BOOL_OP;OR;COMPOSITE_TEST;1;TEST @Value(attribute2print) = tourism'2'BOOL_OP;OR;COMPOSITE_TEST;1;TEST @Value(attribute2print) = waterway'3'FME_NUM_CONDITIONS28___
    -> TestFilter_3
TestFilter_3
    DEFAULT_VALUE = solid_line
    TEST_LIST = "BOOL_OP,OR,COMPOSITE_TEST,""""""1"""""",TEST_CLAUSE,TEST @Value(attribute2print) = boundary",dashed_line,"BOOL_OP,OR,COMPOSITE_TEST,""""""1"""""",TEST_CLAUSE,TEST @Value(attribute2print) = railway",dashed_line,"BOOL_OP,OR,COMPOSITE_TEST,""""""1"""""",TEST_CLAUSE,TEST @Value(attribute2print) = power",dashed_line
    dashed_line -> TestFilter
    solid_line -> PDFStyler_18
PDFStyler_18
    COLOR = @Value(color)
    FILL_COLOR = @Value(color)
    FILL_OPACITY = 0.72
    FONT = Helvetica,14,ITALIC
    LINE_CAP_STYLE_PARAM = Butt Cap
    LINE_DASH_PHASE = @Value(line_phase)
    LINE_JOIN_STYLE_PARAM = Miter Join
    LINE_MITER_LIMIT = 0.0
    LINE_WIDTH = @Value(line_width)
    OPACITY = 1.0
    PDFStyled -> Sorter
TestFilter
    DEFAULT_VALUE = normal
    TEST_LIST = "BOOL_OP,OR,COMPOSITE_TEST,""""""1"""""",TEST_CLAUSE,TEST @Value(attribute2print) = boundary",fillzero
    fillzero -> PDFStyler_20
    normal -> PDFStyler_17
PDFStyler_20
    COLOR = @Value(color)
    FILL_COLOR = 1,1,1
    FILL_OPACITY = 0.00
    FONT = Helvetica,14,ITALIC
    LINE_CAP_STYLE_PARAM = Butt Cap
    LINE_DASH_ARRAY = 2 3 2 3
    LINE_DASH_PHASE = @Value(line_phase)
    LINE_JOIN_STYLE_PARAM = Miter Join
    LINE_MITER_LIMIT = 0.0
    LINE_WIDTH = @Value(line_width)
    OPACITY = 1.0
    PDFStyled -> Sorter
PDFStyler_17
    COLOR = @Value(color)
    FILL_COLOR = @Value(color)
    FILL_OPACITY = 0.15
    FONT = Helvetica,14,ITALIC
    LINE_CAP_STYLE_PARAM = Butt Cap
    LINE_DASH_ARRAY = 2 3 2 3
    LINE_DASH_PHASE = @Value(line_phase)
    LINE_JOIN_STYLE_PARAM = Miter Join
    LINE_MITER_LIMIT = 0.0
    LINE_WIDTH = @Value(line_width)
    OPACITY = 1.0
    PDFStyled -> Sorter
Logger
    LOG_FEATURE = LOG_ONLY
    MAXCOORDS = 20
    MAXFEATS = 20
    MESSAGE = Feature is:
    SEVERITY = INFO

Bookmark: North Arrow
Creator_3
    GEOMTYPE = Geometry Object
    NUM = 1
    CREATED -> Cloner_5
Cloner_5
    COPIES = 5
    COPYATT = _copynum
    COPY -> VertexCreator_5
VertexCreator_5
    MEASURE_TYPE = Continuous
    MISSING_VAL_MODE = Compute
    MODE_NAME = Add Point
    XVAL = FME_CONDITIONAL:DEFAULT_VALUE''BOOL_OP;OR;COMPOSITE_TEST;1 OR 2;TEST @Value(_copynum) = 0;TEST @Value(_copynum) = 4'0'BOOL_OP;OR;COMPOSITE_TEST;1;TEST @Value(_copynum) = 1'1'BOOL_OP;OR;COMPOSITE_TEST;1;TEST @Value(_copynum) = 2'2'BOOL_OP;OR;COMPOSITE_TEST;1;TEST @Value(_copynum) = 3'1'FME_NUM_CONDITIONS5___
    YVAL = FME_CONDITIONAL:DEFAULT_VALUE''BOOL_OP;OR;COMPOSITE_TEST;1 OR 2;TEST @Value(_copynum) = 0;TEST @Value(_copynum) = 4'0'BOOL_OP;OR;COMPOSITE_TEST;1;TEST @Value(_copynum) = 1'2.5'BOOL_OP;OR;COMPOSITE_TEST;1;TEST @Value(_copynum) = 2'0'BOOL_OP;OR;COMPOSITE_TEST;1;TEST @Value(_copynum) = 3'0.8'FME_NUM_CONDITIONS5___
    -> LineBuilder_5
LineBuilder_5
    ACCUM_INPUT_ATTRS = Use Attributes From One Feature
    REMOVE_DUPLICATES = No
    POLYGON -> PDFStyler_6
PDFStyler_6
    COLOR = 0,0,0
    FILL_COLOR = 0,0,0
    FILL_OPACITY = 1.00
    FONT = MS Shell Dlg 2,12,BOLD
    LINE_CAP_STYLE_PARAM = Butt Cap
    LINE_DASH_PHASE = 0
    LINE_JOIN_STYLE_PARAM = Miter Join
    LINE_MITER_LIMIT = 0.0
    LINE_WIDTH = 1.5
    OPACITY = 1.0
    PDFStyled -> PDFPageFormatter [arrow]
North: Creator
    GEOM = <?xml version="1.0" encoding="US_ASCII" standalone="no" ?><geometry><text><point><coord x="0" y="0"/></point><textString>null</textString><textSize>10</textSize><textRotation>0</textRotation></text></geometry>
    GEOMTYPE = Geometry Object
    NUM = 1
    CREATED -> AttributeManager_13
AttributeManager_13
    ATTR_TABLE = SET_TO fme_text_string = N
    -> PDFStyler_14
PDFStyler_14
    COLOR = 0,0,0
    FILL_COLOR = 0,0,0
    FILL_OPACITY = 1.00
    FONT = MS Shell Dlg 2,12,BOLD
    LINE_CAP_STYLE_PARAM = Butt Cap
    LINE_DASH_PHASE = 0
    LINE_JOIN_STYLE_PARAM = Miter Join
    LINE_MITER_LIMIT = 0.0
    LINE_WIDTH = 1.0
    OPACITY = 1.0
    PDFStyled -> PDFPageFormatter [North]

Bookmark: TItle & Signature
Title: Creator
    GEOM = <?xml version="1.0" encoding="US_ASCII" standalone="no" ?><geometry><text><point><coord x="0" y="0"/></point><textString>Cartographic output</textString><textSize>1</textSize><textRotation>0</textRotation></text></geometry>
    GEOMTYPE = Geometry Object
    NUM = 1
    CREATED -> PDFStyler
PDFStyler
    COLOR = 0,0,0
    FILL_COLOR = 0,0,0
    FILL_OPACITY = 0.60
    FONT = Helvetica,16
    LINE_CAP_STYLE_PARAM = Butt Cap
    LINE_DASH_PHASE = 0
    LINE_JOIN_STYLE_PARAM = Miter Join
    LINE_MITER_LIMIT = 0.0
    LINE_WIDTH = 1.0
    OPACITY = 1.0
    PDFStyled -> PDFPageFormatter [Title_Frame]
    PDFStyled -> PDFPageFormatter_2 [header]
Signature: Creator
    GEOM = <?xml version="1.0" encoding="US_ASCII" standalone="no" ?><geometry><text><point><coord x="0" y="0"/></point><textString>HGDR project, INSER SA, 2022</textString><textSize>10</textSize><textRotation>0</textRotation></text></geometry>
    GEOMTYPE = Geometry Object
    NUM = 1
    CREATED -> PDFStyler_2
PDFStyler_2
    COLOR = 0,0,0
    FILL_COLOR = 0,0,0
    FILL_OPACITY = 0.4
    FONT = Helvetica,12,ITALIC
    LINE_CAP_STYLE_PARAM = Butt Cap
    LINE_DASH_PHASE = 0
    LINE_JOIN_STYLE_PARAM = Miter Join
    LINE_MITER_LIMIT = 0.0
    LINE_WIDTH = 1.0
    OPACITY = 1.0
    PDFStyled -> PDFPageFormatter [Signature_Frame]
    PDFStyled -> PDFPageFormatter_2 [signature]

FME custom transformer RGBGradationCalculator
Calculates RGB color values changing gradationally between the specified seed colors, and adds a list attribute (named 
    _color{}
    by default) to the feature, which stores the resulting color values.
    Optionally you can create a new attribute storing a raster palette definition which can be used to add a palette to a raster feature with the RasterPaletteAdder. See the "Raster Palette ***" parameters.
    Color Value Formats
    This transformer supports these formats to represent an RGB (red, green, blue) color value for both seed colors and resulting colors.
    FME Color
    :
    Comma-separated R, G, B decimal point numbers. The valid range of each element is 0.0-1.0.
    HTML Color
    :
    Concatenated R, G, B hexadecimal integers, starting with #. Each element should be two digits, and its valid range is 00-FF.
    Comma-Separated Decimal RGB24
    :
    Comma-separated R, G, B decimal integers. The valid range of each element is 0-255.
    Comma-Separated Hexadecimal RGB24
    : Comma-separated R, G, B hexadecimal integers. The valid range of each element is 0-FF.
    You can specify two or more seed color values separated by 
    semicolons
    . The format of the values can be one of the above formats, but you will have to tell the format to the transformer via the "Format of Seed Colors" parameter. If the format or value of a specified seed color is invalid, the input feature will be output via the 
    <Rejected>
    port.
    Regarding the resulting color values which will be stored into the 
    _color{}
    list, you can choose one of the above formats via the "Format of Destination Colors" parameter.
    A-F within hexadecimal numbers for seed color values will be interpreted in case-insensitive. In the destination color values, lowercase will be used by default, but you can also use uppercase with setting "Yes" to the "Use Uppercase in Hexadecimal" parameter. 
    Seed Colors Setting Examples
    FME Color
    : 1,0,0; 1,1,0; 0,1,0; 0,1,1; 0,0,1
    HTML Color
    : #ff0000; #ffff00; #00ff00; #00ffff; #0000ff
    Comma-Separated Decimal RGB24
    : 255,0,0; 255,255,0; 0,255,0; 0,255,255; 0,0,255
    Comma-Separated Hexadecimal RGB24
    : ff,0,0; ff,ff,0; 0,ff,0; 0,ff,ff; 0,0,ff
Parameters
    Seed Colors (semicolon-separated)
    :
    Specify two or more seed colors separated by 
    semicolons
    .
    Format of Seed Colors
    :
    Select a format which you've used to specify the seed colors.
    Number of Destination Colors
    :
    Specify the number of gradation colors which you need to calculate based on the specified seed colors.This number should be greater than or equal to the number of seed colors. The number of resulting list elements will be equal to this number by default
    . See also the "Adjust Number of Destination Colors" parameter.
    Adjust Number of Destination Colors
    :
    By default, the number of resulting list elements will exactly match the value specified to the "Number of Destination Colors" parameter. In general, however, the list might not contain colors which exactly match the seed colors (except the first and the last). If you need to guarantee that the list will contain every seed color, select "Ceil" or "Floor" in this parameter to adjust the number of destination colors automatically.
    Ceil
    : the transformer will use the number closest to the specified number so that the list contains every seed color, in the range of not less than the specified number. 
    Floor
    : the transformer will use the number closest to the specified number so that the list contains every seed color, in the range of not greater than the specified number. 
    Format of Destination Colors
    :
    Select a format for the resulting color values. 
    Destination Color List Name
    :
    Specify a list name which will store the resulting color values.
    Use Uppercase in Hexadecimal
    :
    If you need to use uppercase A-F for destination color values in the HTML Color or Comma-Separated Hexadecimal RGB24 format, set "Yes" to this parameter.
    Reverse Sequence of Destination Colors
    : 
    If you set "Yes" to this parameter, the sequence of the resulting list elements will be reversed.
    Raster Palette Attribute Name (Optional)
    :
    Optionally specify an attribute name which will store a raster palette definition. 
    Raster Palette Interpretation
    :
    Select an interpretation for the palette definition. Currently this transformer only supports 'RGB24' and 'RGBA32'.
    Raster Palette Alpha Value
    :
    If you select 'RGBA32' in the "Raster Palette Interpretation", specify the alpha value. The specified value will be applied to every entry in the resulting palette definition.
    Raster Palette First Key Value
    :
    The palette key values will be sequential numbers starting with 0 by default, but you can change the first key value via this parameter optionally. The first key value should be an integer greater than or equal to 0.
    Raster Palette Omit Interpretation
    :
    By default, the palette definition starts with a line that specifies the interpretation ('RGB24' etc.), so that it can be set to a raster feature immediately. Optionally you can omit the interpretation line by setting "Yes" to this parameter. This option might be useful if you need to insert one or more special entries (e.g. an entry for Nodata representation) to the first portion of the palette definition later, in conjunction with setting a number greater than 0 to the "Raster Palette First Key Value" parameter.

Parameters:
- SEED =   # Seed Colors (semicolon-separated)
- SEED_FORMAT = FME
- NUM =   # Number of Destination Colors
- ADJUST = None   # Adjust Number of Destination Colors
- DEST_FORMAT = FME
- LIST_NAME = _color   # TYPE:varchar(200) Destination Color List Name
- UPPER_HEX = No   # Use Uppercase in Hexadecimal
- REVERSE = No   # Reverse Sequence of Destination Colors
- PALETTE_ATTR =   # TYPE:varchar(200) Raster Palette Attribute Name (Optional)
- PALETTE_TYPE = RGB24   # Raster Palette Interpretation
- PALETTE_ALPHA = 255   # Raster Palette Alpha Value
- PALETTE_FIRST_KEY = 0   # Raster Palette First Key Value
- PALETTE_OMIT_TYPE = No   # Raster Palette Omit Interpretation

Input (input)
    -> ParameterFetcher
ParameterFetcher
    ATTR_LIST = __rgbcalc.seed {$(SEED)} __rgbcalc.seed_format {$(SEED_FORMAT)} __rgbcalc.num {$(NUM)} __rgbcalc.adjust {$(ADJUST)} __rgbcalc.dest_format {$(DEST_FORMAT)} __rgbcalc.list_name {$(LIST_NAME)} __rgbcalc.upper_hex {$(UPPER_HEX)} __rgbcalc.reverse {$(REVERSE)} __rgbcalc.palette_attr {$(PALETTE_ATTR)} __rgbcalc.palette_first_key {$(PALETTE_FIRST_KEY)} __rgbcalc.palette_type {$(PALETTE_TYPE)} __rgbcalc.palette_alpha {$(PALETTE_ALPHA)} __rgbcalc.palette_omit_type {$(PALETTE_OMIT_TYPE)}
    -> TclCaller
Note: Validate seed color format and values, and create / a temporary list containing the seed values.
TclCaller
    SRC:
      proc createSeedRGBList {} {
          global RGB; set RGB {}
          proc appendRGB {r g b} {
              proc isValid {v} {
                  return [expr [string is double -strict $v] && 0 <= $v && $v <= 1]
              }
              if {[isValid $r] && [isValid $g] && [isValid $b]} {
                  global RGB; lappend RGB [format "%f %f %f" $r $g $b]; return 1
              } else {
                  return 0
              }
          }
          proc trimLeftZero {v} {
              return "[string trimleft [string range $v 0 end-1] {0}][string index $v end]"
          }
          switch [FME_GetAttribute "__rgbcalc.seed_format"] {
              "FME" {
                  set regex "^\\s*(\[^\\s\]+)\\s*,\\s*(\[^\\s\]+)\\s*,\\s*(\[^\\s\]+)\\s*\$"
                  proc conv {v} {return [trimLeftZero $v]}
              }
              "HTML" {
                  set regex "^\\s*#(\[A-F\\d\]{2})(\[A-F\\d\]{2})(\[A-F\\d\]{2})\\s*\$"
                  proc conv {v} {return [expr [scan $v %x]/255.0]}
              }
              "CSV_DEC_RGB24" {
                  set regex "^\\s*(\\d+)\\s*,\\s*(\\d+)\\s*,\\s*(\\d+)\\s*\$"
                  proc conv {v} {return [expr [trimLeftZero $v]/255.0]}
              }
              "CSV_HEX_RGB24" {
                  set regex "^\\s*(\[A-F\\d\]+)\\s*,\\s*(\[A-F\\d\]+)\\s*,\\s*(\[A-F\\d\]+)\\s*\$"
                  proc conv {v} {return [expr [scan $v %x]/255.0]}
              }
          }
          foreach s [split [FME_GetAttribute "__rgbcalc.seed"] {;}] {
              if {![regexp -nocase $regex $s m r g b] || ![appendRGB [conv $r] [conv $g] [conv $b]]} {
                  return "format or value of a seed color is invalid: $s"
              }
          }
          if {1 < [llength $RGB]} {
              if {[llength $RGB] <= [FME_GetAttribute "__rgbcalc.num"]} {
                  for {set i 0} {$i < [llength $RGB]} {incr i} {
                      FME_SetAttribute "__rgbcalc.seed{$i}" [lindex $RGB $i]
                  }
              } else {
                  return "the number of destination colors is less than the number of seed colors."
              }
          } else {
              return "the number of seed colors is less than 2."
          }
          if {0 < [string length [FME_GetAttribute "__rgbcalc.palette_attr"]]} {
              if {[FME_GetAttribute "__rgbcalc.palette_first_key"] < 0} {
                  return "raster palette first key is less than 0."
              }
              if {[string equal [FME_GetAttribute "__rgbcalc.palette_type"] "RGBA32"]} {
                  set alpha [FME_GetAttribute "__rgbcalc.palette_alpha"]
                  if {$alpha < 0 || 255 < $alpha} {
                      return "raster palette alpha value is out of range."
                  }
              }
          }
      }
    TCLPROG = createSeedRGBList
    VAL_ATTR = __rgbcalc.error_msg
    -> Tester
Tester
    BOOL_OP = OR
    TEST_CLAUSE = TEST @Value(__rgbcalc.error_msg) = ""
    TEST_MODE = Automatic
    PASSED -> PythonCaller
    FAILED -> AttributeRenamer
PythonCaller
    HIDE_ATTRIBUTES = __rgbcalc.adjust __rgbcalc.dest_format __rgbcalc.error_msg __rgbcalc.list_name __rgbcalc.num __rgbcalc.palette_alpha __rgbcalc.palette_attr __rgbcalc.palette_first_key __rgbcalc.palette_omit_type __rgbcalc.palette_type __rgbcalc.reverse __rgbcalc.seed __rgbcalc.seed_format __rgbcalc.upper_hex
    NEW_ATTRIBUTES = __color_list__{} __raster_palette__
    PYTHONSOURCE:
      # 2016-04-15,  Takashi Iijima,  Original Implementation
      # 2016-04-17,  Takashi Iijima,  Changed destination list name; added a code to remove temporary attributes.
      # 2016-04-18,  Takashi Iijima,  Added Raster Palette attribute creation.

      import fme
      import fmeobjects, math, locale

      class RGBGradationCalculator(object):
          def __init__(self):
              toDec = lambda v: int(round(v * 255))
              def toHex(v):
                  h = hex(toDec(v))[2:]
                  return h if 1 < len(h) else '0%s' % h
              self.funcColor = { \
                  'FME': lambda r,g,b: '%f,%f,%f' % (r, g, b), \
                  'HTML': lambda r,g,b: '#%s%s%s' % (toHex(r), toHex(g), toHex(b)), \
                  'CSV_DEC_RGB24': lambda r,g,b: '%d,%d,%d' % (toDec(r), toDec(g), toDec(b)), \
                  'CSV_HEX_RGB24': lambda r,g,b: '%s,%s,%s' % (toHex(r), toHex(g), toHex(b)), \
              }

          def input(self, feature):
              # Collect seed RGB values.
              seedRGB = [[float(v) for v in s.split()] for s in feature.getAttribute('__rgbcalc.seed{}')]
              if feature.getAttribute('__rgbcalc.reverse') == 'Yes':
                  seedRGB.reverse()

              # Calculate destination RGB values by linear interpolation.
              destRGB = []
              nSeed, nDest = len(seedRGB), int(feature.getAttribute('__rgbcalc.num'))
              adjust = feature.getAttribute('__rgbcalc.adjust')
              if adjust == 'Ceil':
                  nDest = int(math.ceil(float(nDest - nSeed) / (nSeed - 1))) * (nSeed - 1) + nSeed
              elif adjust == 'Floor':
                  nDest = int(math.floor(float(nDest - nSeed) / (nSeed - 1))) * (nSeed - 1) + nSeed
              d, k = 1.0 / (nSeed - 1), 1
              for s in [float(i) / (nDest - 1) for i in range(nDest)]:
                  while k < nSeed - 1 and d * k < s:
                      k += 1
                  r = s / d - (k - 1)
                  destRGB.append([a + (b - a) * r for a, b in zip(seedRGB[k-1], seedRGB[k])])

              # Save destination colors into a list attribute.
              color = self.funcColor[feature.getAttribute('__rgbcalc.dest_format')]
              upper = (feature.getAttribute('__rgbcalc.upper_hex') == 'Yes')
              for i, v in enumerate(destRGB):
                  feature.setAttribute('__color_list__{%d}' % i, color(*v).upper() if upper else color(*v))

              # Create raster palette attribute when palette attribute name is specified.
              if feature.getAttribute('__rgbcalc.palette_attr'):
                  rows = []
                  firstKey = int(feature.getAttribute('__rgbcalc.palette_first_key'))
                  type = feature.getAttribute('__rgbcalc.palette_type')
                  if type == 'RGB24':
                      color = self.funcColor['CSV_DEC_RGB24']
                      rows = ['%d %s' % (firstKey + i, color(*v)) for i, v in enumerate(destRGB)]
                  elif type == 'RGBA32':
                      color = self.funcColor['CSV_DEC_RGB24']
                      alpha = int(feature.getAttribute('__rgbcalc.palette_alpha'))
                      rows = ['%d %s,%d' % (firstKey + i, color(*v), alpha) for i, v in enumerate(destRGB)]
                  palette = '\r\n'.join(rows)
                  if feature.getAttribute('__rgbcalc.palette_omit_type') == 'No':
                      palette = '%s\r\n%s' % (type, palette)
                  feature.setAttribute('__raster_palette__', palette)

              # Remove temporary attributes, then output the feature.
              feature.removeAttrsWithPrefix('__rgbcalc.')
              self.pyoutput(feature)
    PYTHONSYMBOL = RGBGradationCalculator
    -> BulkAttributeRenamer
BulkAttributeRenamer
    ATTRCHOICE = All Attributes
    CASE_DISP = yes
    PATTERN_ACTION_DISP = String Replace
    REPLACE_PATTERN = __color_list__
    REPLACE_STR = $(LIST_NAME)
    -> BulkAttributeRenamer_2
BulkAttributeRenamer_2
    ATTRCHOICE = Selected Attributes
    ATTRLIST = __raster_palette__
    PATTERN_ACTION_DISP = Regular Expression Replace
    REPLACE_PATTERN = .+
    REPLACE_STR = $(PALETTE_ATTR)
    -> Output (output)
Output (output)
AttributeRenamer
    ATTR_LIST = __rgbcalc.error_msg,_rejected_reason,
    -> AttributeRemover
AttributeRemover
    REMOVE_ATTRS = __rgbcalc.adjust,__rgbcalc.dest_format,__rgbcalc.list_name,__rgbcalc.num,__rgbcalc.palette_alpha,__rgbcalc.palette_attr,__rgbcalc.palette_first_key,__rgbcalc.palette_type,__rgbcalc.reverse,__rgbcalc.seed,__rgbcalc.seed_format,__rgbcalc.upper_hex,__rgbcalc.palette_omit_type
    -> <Rejected> (output)
<Rejected> (output)
