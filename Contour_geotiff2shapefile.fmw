FME workspace Contour_geotiff2shapefile.fmw

Parameters:
- SourceDataset_GEOTIFF = $(FME_MF_DIR)output_ITA_CHE\02_DEM\DEM_2011_ITA_CHE.tif   # Source GeoTIFF File(s)
- DestDataset_SHAPEFILE = $(FME_MF_DIR)output_ITA_CHE\02_DEM   # Destination Esri Shapefile Folder
- ISO_merged =   # ISO merged

Readers:
- GEOTIFF_1: GEOTIFF from $(SourceDataset_GEOTIFF)

Writers:
- SHAPEFILE_1: SHAPEFILE to $(DestDataset_SHAPEFILE)

GEOTIFF (reader GEOTIFF_1)
    -> ContourGenerator [POINTS/LINES]
ContourGenerator
    CONTOUR_DIMENSION = 3
    CONTOUR_INTERVAL = 20
    ELEV_ATTR = Elevation
    IGNORE_INPUT_ON_INTERVAL = Perturb Input Points On Contour Interval
    TOLERANCE = 0
    CONTOURS -> LineCombiner
LineCombiner
    ACCUM_ATTRS_NAME = Use Attributes From One Feature
    BREAK = no
    BREAK_CONNECTION_ATTRIBUTES = Elevation
    CONNECT_Z_MODE = First Wins
    CONSIDER_NODE_ELEVATION = no
    DEAGGREGATE_GEOMETRY = Deaggregate
    JUNCTIONS_IGNORE_ATTRIBUTES = No
    LINES_AS_SEGMENTS = No
    PRESERVE = no
    TOPOLOGY = End noded
    LINE -> Generalizer
Note: Generalizer [Generalizer Version 4] / Transformer: / Group By Mode: Process At End (Blocking) / Algorithm: / Algorithm: NURBfit (Smooth) / Parameters: / Preserve Shared Boundaries: No / Preserve Path Segments: No / NURBfit Parameters: / Degree of Basis Polynomial: 2 / Segment Length: 0
Generalizer
    ALG_TEXT = NURBfit (Smooth)
    DEGREE = 2
    PRESERVE = No
    PRESERVE_PATHS = No
    SEGMENT_LENGTH = 0
    -> Contour_2011_ (writer SHAPEFILE_1)
Contour_2011_ (writer SHAPEFILE_1)
    attributes: fme_basena char(50)
